-- **************************************************************
-- Cerent-454-MIB module
--
-- This module contains the objects and events for the
-- Cisco ONS 15454

-- Copyright (c) 1998-1999 by Cerent Corporation, Inc.
-- Copyright (c) 2000-2002, 2004-2005 by Cisco Systems, Inc.
-- All rights reserved.
--
-- **************************************************************

CERENT-454-MIB DEFINITIONS ::= BEGIN

IMPORTS
    MODULE-IDENTITY,
    OBJECT-TYPE,
    OBJECT-IDENTITY,
    NOTIFICATION-TYPE,
    Integer32,
    Unsigned32,
    Counter32
                      FROM SNMPv2-SMI
    TEXTUAL-CONVENTION,
    DisplayString,
    TruthValue,
    TimeStamp
                      FROM SNMPv2-TC
    MODULE-COMPLIANCE,
    OBJECT-GROUP,
    NOTIFICATION-GROUP
                      FROM SNMPv2-CONF
    cerentProducts,
    cerentModules
                      FROM CERENT-GLOBAL-REGISTRY
    CerentNotificationClass,
    CerentMonitorType,
    CerentLocation,
    CerentPeriod,
    CerentPortNumber
                      FROM CERENT-TC;

cerent454MibModule MODULE-IDENTITY
    LAST-UPDATED "0410010000Z" -- 2004/Oct/01
    ORGANIZATION "Cisco Systems, Inc."
    CONTACT-INFO
        "         support@Cisco.com

         Postal:  Cisco Systems
                  1450 N. McDowell Blvd.
                  Petaluma, CA  94954
                  USA

            Tel:  +1-877-323-7368"
    DESCRIPTION
        "This module provides the definitions for
         objects for managing Cisco OTBU ONS 15454."

    REVISION "0410010000Z" -- 2004/Oct/01
    DESCRIPTION
        "This file can be used with R5.0  release."
         
    ::= { cerentModules 20 }

cerent454Mib OBJECT-IDENTITY
      STATUS      current
      DESCRIPTION
            "The is the node under which all Cisco ONS 15454
             specific mib object are located."
      ::= { cerentProducts 10 }

cerent454Conformance OBJECT-IDENTITY
      STATUS      current
      DESCRIPTION
            "This node is created compliance. Has
             objects as required by the RFCs"
      ::= { cerent454Mib 10 }

--  ********************************************************

cerentCommonObjects OBJECT-IDENTITY
      STATUS      current
      DESCRIPTION
            "The objects here are expected to be
             used by all Cisco OTBU Products.
             These will be mixed with specific
             objects of the product-specific branch."
      ::= { cerent454Mib 100 }
--
cerentCommonEvents OBJECT-IDENTITY
      STATUS      current
      DESCRIPTION
            "This branch is similar to cerentCommonObjects,
             except that this will have only events"
      ::= { cerent454Mib 200 }

--  ********************************************************

cerent454Groups OBJECT-IDENTITY
      STATUS      current
      DESCRIPTION
            ""
      ::= { cerent454Conformance 10 }

cerent454Compliance OBJECT-IDENTITY
      STATUS      current
      DESCRIPTION
            ""
      ::= { cerent454Conformance 20 }

-- **************************************************************
-- Cisco ONS 15454 specific textual conventions
-- **************************************************************

Cerent454AlarmType ::= TEXTUAL-CONVENTION
   -- DISPLAY-HINT "d"
   STATUS current
   DESCRIPTION
       "This TC is used by the NMS to map the alarm type
        received by the trap and and display the string
        shown in LHS."
   SYNTAX INTEGER {
       alarmUnknown                                      (  1 ),
       alarmCutoffIsInManualMode                         ( 10 ),
       failureDetectedExternalToTheNE                    ( 20 ),
       externalError                                     ( 30 ),
       excessiveSwitching                                ( 40 ),
       sdccTerminationFailure                            ( 50 ),
       incomingFailureCondition                          ( 60 ),
       alarmIndicationSignal                             ( 70 ),
       alarmIndicationSignalLine                         ( 80 ),
       alarmIndicationSignalPath                         ( 90 ),
       alarmIndicationSignalVT                           ( 100 ),
       channelFailureAPS                                 ( 110 ),
       channelByteFailureAPS                             ( 120 ),
       channelProtectionSwitchingChannelMatchFailureAPS  ( 130 ),
       channelAutomaticProtectionSwitchModeMismatchAPS   ( 140 ),
       channelFarEndProtectionLineFailureAPS             ( 150 ),
       inconsistentAPSCode                               ( 160 ),
       improperAPSCode                                   ( 170 ),
       nodeIdMismatch                                    ( 180 ),
       channelDefaultKAPS                                ( 190 ),
       connectionLoss                                    ( 200 ),

       bipolarViolation                                  ( 210 ),
       carrierLossOnTheLAN                               ( 220 ),
       concatenationErrorSTS                             ( 230 ),
       excessCollisionsOnTheLAN                          ( 240 ),
       facilityCriticalAlarmCausedByDS3FacilityFailure   ( 250 ),
       farEndAIS                                         ( 260 ),
       farEndMultipleDS1LOSDetectedOnDS3                 ( 270 ),
       farEndDS1EqptFailNonServiceAffecting              ( 280 ),
       farEndDS1EqptFailServiceAffecting                 ( 290 ),
       farEndSingleDS1LOS                                ( 300 ),
       farEndDS3EqptFailNonServiceAffecting              ( 310 ),
       farEndDS3EqptFailServiceAffecting                 ( 320 ),
       farEndCommonEquipmentFailureNonServiceAffecting   ( 330 ),
       farEndIDLE                                        ( 340 ),
       farEndLOS                                         ( 350 ),
       farEndLOF                                         ( 360 ),
       farEndBlockError                                  ( 370 ),
       ds3IdleCondition                                  ( 380 ),
       lossOfFrame                                       ( 390 ),
       lossOfPointer                                     ( 400 ),

       lossOfPointerPath                                 ( 410 ),
       lossOfPointerVT                                   ( 420 ),
       lossOfSignal                                      ( 430 ),
       outOfFrame                                        ( 440 ),
       pathSelectorInabilityToSwitchToAValidSignal       ( 450 ),
       remoteAlarmIndication                             ( 460 ),
       remoteFailureIndication                           ( 470 ),
       remoteFailureIndicationLine                       ( 480 ),
       remoteFailureIndicationPath                       ( 490 ),
       remoteFailureIndicationVT                         ( 500 ),

       signalDegrade                                     ( 510 ),
       severelyErroredFrame                              ( 520 ),
       signalFailure                                     ( 530 ),
       signalLabelMismatchFailure                        ( 540 ),
       payloadDefectIndication                           ( 550 ),

       payloadDefectIndicationPath                            ( 560 ),
       payloadLabelMismatchPath                               ( 570 ),
       signalLabelMismatchFailurePayloadLabelMismatchVT       ( 580 ),
       unequippedPath                                         ( 590 ),
       signalLabelMismatchFailureUnequippedVT                 ( 600 ),
       lossOfSynchronization                                  ( 610 ),
       outOfSynchronization                                   ( 620 ),
       primarySynchronizationReferenceFailure                 ( 630 ),
       secondarySynchronizationReferenceFailure               ( 640 ),
       thirdSynchronizationReferenceFailure                   ( 650 ),
       fourthSynchronizationReferenceFailure                  ( 660 ),
       fifthSynchronizationReferenceFailure                   ( 670 ),
       sixthSynchronizationReferenceFailure                   ( 680 ),

       failedToReceiveSynchronizationStatusMessage             ( 690 ),
       synchronizationStatusMessagesAreDisabledOnThisInterface ( 700 ),
       primaryReferenceSourceStratum1Traceable                 ( 710 ),
       synchronizedTraceabilityUnknown                         ( 720 ),
       stratum2Traceable                                       ( 730 ),
       transitNodeClockTraceable                               ( 740 ),

       stratum3ETraceable                    ( 750 ),
       stratum3Traceable                     ( 760 ),
       sonetMinimumClockTraceable            ( 770 ),
       stratum4Traceable                     ( 780 ),
       doNotUseForSynchronization            ( 790 ),
       reservedForNetworkSynchronizationUse  ( 800 ),

       outgoingFailureCondition          ( 810 ),
       remoteDefectIndicationLine        ( 820 ),
       remoteDefectIndicationPath        ( 830 ),
       freeRunningSynchronizationMode    ( 840 ),
       holdoverSynchronizationMode       ( 850 ),
       fastStartSynchronizationMode      ( 860 ),
       internalHardwareFaultOrFailure    ( 870 ),
       errorInternalToTheNEDetected      ( 880 ),
       internalMessageError              ( 890 ),
       mismatchOfEquipmentAndAttributes  ( 900 ),
       watchdogTimerTimeout              ( 910 ),
       softwareFaultOrFailure            ( 920 ),
       softwareFaultDataIntegrityFault   ( 930 ),
       programFailure                    ( 940 ),

       controlEquipmentFailure                                 ( 950 ),
       controlEquipmentPrimaryNonVolatileBackupMemoryFailure   ( 960 ),
       cntrlEqptSecondaryNonVolatileBackupMemoryFailed ( 970 ),
       controlEquipmentControlBusFailure                       ( 980 ),
       controlEquipmentControlBus1Failure                      ( 990 ),
       controlEquipmentControlBus2Failure                      ( 1000 ),

       communicationFailureTCCAToShelfSLOT1      ( 1010 ),
       communicationFailureTCCAToShelfSLOT2      ( 1020 ),
       communicationFailureTCCAToShelfSLOT3      ( 1030 ),
       communicationFailureTCCAToShelfSLOT4      ( 1040 ),
       communicationFailureTCCAToShelfSLOT5      ( 1050 ),
       communicationFailureTCCAToShelfSLOT6      ( 1060 ),
       communicationFailureTCCAToShelfSLOT7      ( 1070 ),
       communicationFailureTCCAToShelfSLOT8      ( 1080 ),
       communicationFailureTCCAToShelfSLOT9      ( 1090 ),
       communicationFailureTCCAToShelfSLOT10     ( 1100 ),
       communicationFailureTCCAToShelfSLOT11     ( 1110 ),
       communicationFailureTCCAToShelfSLOT12     ( 1120 ),
       communicationFailureTCCAToShelfSLOT13     ( 1130 ),
       communicationFailureTCCAToShelfSLOT14     ( 1140 ),
       communicationFailureTCCAToShelfSLOT15     ( 1150 ),
       communicationFailureTCCAToShelfSLOT16     ( 1160 ),
       communicationFailureTCCAToShelfSLOT17     ( 1170 ),
       tccAToDCCAProcessorCommunicationFailure   ( 1180 ),
       communicationFailureTCCBToShelfSLOT1      ( 1190 ),
       communicationFailureTCCBToShelfSLOT2      ( 1200 ),
       communicationFailureTCCBToShelfSLOT3      ( 1210 ),
       communicationFailureTCCBToShelfSLOT4      ( 1220 ),
       communicationFailureTCCBToShelfSLOT5      ( 1230 ),
       communicationFailureTCCBToShelfSLOT6      ( 1240 ),
       communicationFailureTCCBToShelfSLOT7      ( 1250 ),
       communicationFailureTCCBToShelfSLOT8      ( 1260 ),
       communicationFailureTCCBToShelfSLOT9      ( 1270 ),
       communicationFailureTCCBToShelfSLOT10     ( 1280 ),
       communicationFailureTCCBToShelfSLOT11     ( 1290 ),
       communicationFailureTCCBToShelfSLOT12     ( 1300 ),
       communicationFailureTCCBToShelfSLOT13     ( 1310 ),
       communicationFailureTCCBToShelfSLOT14     ( 1320 ),
       communicationFailureTCCBToShelfSLOT15     ( 1330 ),
       communicationFailureTCCBToShelfSLOT16     ( 1340 ),
       communicationFailureTCCBToShelfSLOT17     ( 1350 ),
       communicationFailureTCCPBToTCCJBprocessor ( 1360 ),

       controlEquipmentControlCommunicationsEquipmentFailure ( 1370 ),
       controlEquipmentControlProcessorFailure               ( 1380 ),
       controlEquipmentWorkingMemoryFailure                  ( 1390 ),

       interconnectionEquipmentFailure                     ( 1400 ),
       interconnectionEquipmentFailurePayloadBus1Working    ( 1410 ),
       interconnectionEquipmentFailurePayloadBus2Working    ( 1420 ),
       interconnectionEquipmentFailurePayloadBus3Working    ( 1430 ),
       interconnectionEquipmentFailurePayloadBus4Working    ( 1440 ),
       interconnectionEquipmentFailurePayloadBus5Working    ( 1450 ),
       interconnectionEquipmentFailurePayloadBus6Working    ( 1460 ),
       interconnectionEquipmentFailurePayloadBus7Working    ( 1470 ),
       interconnectionEquipmentFailurePayloadBus8Working    ( 1480 ),
       interconnectionEquipmentFailurePayloadBus9Working    ( 1490 ),
       interconnectionEquipmentFailurePayloadBus10Working   ( 1500 ),
       interconnectionEquipmentFailurePayloadBus11Working   ( 1510 ),
       interconnectionEquipmentFailurePayloadBus12Working   ( 1520 ),
       interconnectionEquipmentFailurePayloadBus1Protect   ( 1530 ),
       interconnectionEquipmentFailurePayloadBus2Protect   ( 1540 ),
       interconnectionEquipmentFailurePayloadBus3Protect   ( 1550 ),
       interconnectionEquipmentFailurePayloadBus4Protect   ( 1560 ),
       interconnectionEquipmentFailurePayloadBus5Protect   ( 1570 ),
       interconnectionEquipmentFailurePayloadBus6Protect   ( 1580 ),
       interconnectionEquipmentFailurePayloadBus7Protect   ( 1590 ),
       interconnectionEquipmentFailurePayloadBus8Protect   ( 1600 ),
       interconnectionEquipmentFailurePayloadBus9Protect   ( 1610 ),
       interconnectionEquipmentFailurePayloadBus10Protect  ( 1620 ),
       interconnectionEquipmentFailurePayloadBus11Protect  ( 1630 ),
       interconnectionEquipmentFailurePayloadBus12Protect  ( 1640 ),
       interconnectionEqptTimeSlotInterchangeEqptFailure   ( 1650 ),

       equipmentFailure                                    ( 1660 ),
       highTemperature                                     ( 1670 ),
       equipmentFailureInvalidMACAddress                   ( 1680 ),
       equipmentFailureBoardFailure                        ( 1690 ),
       diagnosticFailure                                   ( 1700 ),
       equipmentFailureMediumAccessControl                 ( 1710 ),
       facilityTerminationEquipmentFailure                 ( 1720 ),
       automaticLaserShutoffDueToHighTemperature           ( 1730 ),
       failureToReleaseFromProtection                      ( 1740 ),
       facilityTerminationEquipmentReceiverFailure         ( 1750 ),
       facilityTerminationEquipmentTransmitFailure         ( 1760 ),
       facilityTerminationEquipmentReceiverMissing         ( 1770 ),
       facilityTerminationEquipmentTransmitterMissing      ( 1780 ),
       failureToSwitchToProtection                         ( 1790 ),
       failureToSwitchToProtectionRing                     ( 1800 ),

       failureToSwitchToProtectionSpan                     ( 1810 ),
       failureToSwitchToProtectionPath                     ( 1820 ),
       failureOfCoolingFanTray                             ( 1830 ),
       equipmentUnitPlugIn                                 ( 1840 ),
       nePowerFailureAtConnector                           ( 1850 ),
       powerFailureFuseAlarm                               ( 1860 ),
       synchronizationUnitFailure                          ( 1870 ),
       synchronizationSwitchingEquipmentFailure            ( 1880 ),
       equipmentUnitUnplug                                 ( 1890 ),
       loopback                                            ( 1900 ),

       loopbackDueToFEACCommandDS1                         ( 1910 ),
       loopbackCommandSentToFarEndDS1                      ( 1920 ),
       ds3LoopbackDueToFEACCommand                         ( 1930 ),
       loopbackCommandSentToFarEndDS3                      ( 1940 ),
       loopbackDueToFarEndCommandDS2                       ( 1950 ),
       loopbackCommandSentToFarEndDS2                      ( 1960 ),
       loopbackFacility                                    ( 1970 ),
       loopbackNetwork                                     ( 1980 ),
       loopbackTerminal                                    ( 1990 ),
       manuallyCausedAbnormalCondition                     ( 2000 ),
       newRootDiscoveredInBridgedNetwork                   ( 2010 ),
       topologyChangeDiscoveredInBridgedNetwork            ( 2020 ),
       normalCondition                                     ( 2030 ),
       embeddedOperationsChannelFailureLinkDown            ( 2040 ),
       peerStateMismatch                                   ( 2050 ),
       proceduralError                                     ( 2060 ),
       improperRemoval                                     ( 2070 ),
       duplicateNodeID                                     ( 2080 ),
       blsrOutOfSync                                       ( 2090 ),
       resynchronizedBLSRTables                            ( 2100 ),
       protectionUnitNotAvailable                          ( 2110 ),
       performanceMonitorThresholdCrossingAlert            ( 2120 ),
       occurrenceOfAProtectionSwitchingEvent               ( 2130 ),
       recoveryOrServiceProtectionActionHasBeenInitiated   ( 2140 ),
       automaticSystemReset                                ( 2150 ),
       automaticUPSRSwitchCausedByAIS          ( 2160 ),
       automaticUPSRSwitchCausedByLOP          ( 2170 ),
       automaticUPSRSwitchCausedByUneq         ( 2180 ),
       automaticUPSRSwitchCausedByPDI          ( 2190 ),
       automaticUPSRSwitchCausedBySfber        ( 2200 ),
       automaticUPSRSwitchCausedBySdber        ( 2210 ),
       coldRestart                              ( 2220 ),
       workingFacilityOrEqptForcedSwitchedToWorking      ( 2230 ),
       workingFacilityOrEqptForcedSwitchedToWorkingRing  ( 2240 ),
       workingFacilityOrEqptForcedSwitchedToWorkingSpan  ( 2250 ),
       workingFacilityOrEqptForcedSwitchedProtectionUnit ( 2260 ),

       workingFacilityOrEqptForcedSwitchedProtectionUnitRing ( 2270 ),
       workingFacilityOrEqptForcedSwitchedProtectionUnitSpan ( 2280 ),
       workingFacilityOrEqptForcedSwitchedProtectionUnitPath ( 2290 ),

       initializationInitiated   ( 2300 ),
       lockoutOfProtection       ( 2310 ),
       lockoutOfProtectionRing   ( 2320 ),
       lockoutOfProtectionSpan   ( 2330 ),
       lockoutOfProtectionPath   ( 2340 ),
       lockoutOfWorking          ( 2350 ),
       lockoutOfWorkingRing      ( 2360 ),
       lockoutOfWorkingSpan      ( 2370 ),

       manualSystemReset         ( 2380 ),

       manualSwitchToInternalClock     ( 2390 ),
       manualSwitchToPrimaryReference  ( 2400 ),
       manualSwitchToSecondReference   ( 2410 ),
       manualSwitchToThirdReference    ( 2420 ),
       manualSwitchToFourthReference   ( 2430 ),
       manualSwitchToFifthReference    ( 2440 ),
       manualSwitchToSixthReference    ( 2450 ),

       manualSwitchOfWorkingFacilityOrEqptToProtectionRing   ( 2460 ),
       manualSwitchOfWorkingFacilityOrEqptToProtectionSpan   ( 2470 ),
       manualSwitchOfWorkingFacilityOrEqptToProtection       ( 2480 ),
       manualSwitchOfWorkingFacilityOrEqptToProtectionUnit   ( 2490 ),
       workingFacilityOrEqptManualSwitchToProtectionUnitRing ( 2500 ),
       workingFacilityOrEqptManualSwitchToProtectionUnitSpan ( 2510 ),
       manualSwitchOfWorkingFacilityOrEqptToProtectionPath   ( 2520 ),

       powerFailureRestart        ( 2530 ),
       ringIsSquelchingTraffic    ( 2540 ),
       softwareDownloadInProgress ( 2550 ),

       switchToInternalClock      ( 2560 ),
       switchToPrimaryReference   ( 2570 ),
       switchToSecondaryReference ( 2580 ),
       switchToThirdReference     ( 2590 ),
       switchToFourthReference    ( 2600 ),
       switchToFifthReference     ( 2610 ),
       switchToSixthReference     ( 2620 ),

       systemReboot                                        ( 2630 ),
       switchedBackToWorking                               ( 2640 ),
       switchedToProtection                                ( 2650 ),
       warmRestart                                         ( 2660 ),
       ringIsInWaitToRestoreState                          ( 2670 ),
       manualSwitchRequest            ( 2680 ),
       forcedSwitchRequest             ( 2690 ),
       lockoutSwitchRequest            ( 2700 ),

       rmonHistoriesAndAlarmsReset                ( 2710 ),
       rmonThresholdCrossingAlarm                 ( 2720 ),
       alarmsSuppressedByUserCommand              ( 2730 ),
       alarmsSuppressedForMaintenance             ( 2740 ),
       switchingMatrixModuleFailure               ( 2750 ),
       lanConnectionPolarityReversed               ( 2760 ),
       autonomousPerformanceMonitoringReportMessageInhibited               ( 2780 ),
       ioSlotToXCONCommunicationFailure               ( 2790 ),

         -- Intentional gap

       stsPathTraceIdentifierMismatch             ( 2800 ),
       nodePowerFailureAtConnectorA               ( 2810 ),
       nodePowerFailureAtConnectorB               ( 2820 ),
       freeMemoryOnCardVeryLow                    ( 2830 ),
       freeMemoryOnCardNearZero                   ( 2840 ),

       exerciseRing                               ( 2850 ),
       exerciseSpan                               ( 2860 ),
       squelchingPath                             ( 2870 ),
       extraTrafficPreempted                      ( 2880 ),

       farEndLockoutOfWorkingRing                 ( 2890 ),
       farEndLockoutOfWorkingSpan                 ( 2900 ),
       farEndLockoutOfProtectionRing              ( 2910 ),
       farEndLockoutOfProtectionAllSpans          ( 2920 ),

       farEndWorkingFacilityForcedToSwitchToProtectionUnitRing ( 2930 ),
       farEndWorkingFacilityForcedToSwitchToProtectionUnitSpan ( 2940 ),

       farEndManualSwitchOfWorkingFacilityToProtectionUnitRing ( 2950 ),
       farEndManualSwitchOfWorkingFacilityToProtectionUnitSpan ( 2960 ),
       farEndExerciseRing                                      ( 2970 ),
       farEndExerciseSpan                                      ( 2980 ),
       farEndBERThresholdPassedForSignalFailureRing ( 2990 ),
       farEndBERThresholdPassedForSignalFailureSpan ( 3000 ),
       farEndBERThresholdPassedForSignalDegradeRing ( 3010 ),
       farEndBERThresholdPassedForSignalDegradeSpan ( 3020 ),
       channelFarEndProtectionLineSignalDegradeAPS  ( 3030 ),

       ringSwitchIsActiveOnTheEastSide      ( 3040 ),
       ringSwitchIsActiveOnTheWestSide      ( 3050 ),
       spanSwitchIsActiveOnTheEastSide      ( 3060 ),
       spanSwitchIsActiveOnTheWestSide      ( 3070 ),

       uniDirectionalFullPassThroughIsActive  ( 3080 ),
       biDirectionalFullPassThroughIsActive   ( 3090 ),

       kBytePassThroughIsActive        ( 3100 ),
       ringIsSegmented                 ( 3110 ),
       ringTopologyIsUnderConstruction ( 3120 ),

       lockoutOfProtectionAllSpans                   ( 3130 ),
       farEndOfFiberIsProvisionedWithDifferentRingID ( 3140 ),
       bothEndsOfFiberProvisionedAsEastOrBothAsWest  ( 3150 ),
       securityInvalidLoginUsernameSeeAuditTrail     ( 3160 ),

       autonomousMessagesInhibited        ( 3170 ),
       trafficStormLANtemporarilyDisabled ( 3180 ),

       tl1ReptDbchgMessagesInhibited ( 3190 ),
       userIdHasExpired              ( 3200 ),
       partialFanFailure             ( 3210 ),
       forceSwitchRequestOnRing      ( 3220 ),
       forceSwitchRequestOnSpan      ( 3230 ),
       lockoutSwitchRequestOnRing    ( 3240 ),
       lockoutSwitchRequestOnSpan    ( 3250 ),
       manualSwitchRequestOnRing     ( 3260 ),
       manualSwitchRequestOnSpan     ( 3270 ),

       communicationFailurePeerToPeerSlotControlBusA  ( 3280 ),
       communicationFailurePeerToPeerSlotControlBusB  ( 3290 ),
       controllerAToShelfSlotCommunicationFailure   	( 3300 ),
       controllerBToShelfSlotCommunicationFailure     ( 3310 ),

       interconnectionEquipmentFailureWorkingPayloadBus	( 3320 ),
       interconnectionEquipmentFailureProtectPayloadBus ( 3330 ),
       inhibitSwitchToProtectRequestOnEquipment ( 3340 ),
       inhibitSwitchToWorkingRequestOnEquipment ( 3350 ),

       berThresholdExceededForSignalDegradeLine ( 3360 ),
       berThresholdExceededForSignalDegradePath ( 3370 ),
       berThresholdExceededForSignalFailureLine ( 3380 ),
       berThresholdExceededForSignalFailurePath ( 3390 ),

       exerciseRingCompleted                  ( 3400 ),
       exerciseSpanCompleted                  ( 3410 ),
       spanIsInWaitToRestoreState             ( 3420 ),

       exerciseRingFailed                     ( 3430 ),
       exerciseSpanFailed                     ( 3440 ),
       farEndLockoutOfProtectionChannelInSpan ( 3450 ),

       manufacturingEepromFailure             ( 3460 ),
       replaceableEquipmentIsMissing          ( 3470 ),
       softwareDownloadFailed                 ( 3480 ),
       extraTrafficDropped                    ( 3490 ),

       pktLossDueToOversubscribedXmit ( 3500 ),
       pktLossDueToOversubscribedRcv  ( 3510 ),
       excessiveEthernetFlowCtlXmited ( 3520 ),
       excessiveEthernetFlowCtlRecvd  ( 3530 ),
       transportLayerFailure          ( 3540 ),
       etherHdgeInternalFifoUnderrun  ( 3550 ),

       synchronizationReferenceFrequencyOutOfBounds  ( 3560 ),
       ntpOrSntpHostFailure                          ( 3570 ),
       peerCardNotResponding                         ( 3580 ),
       alarmsAndEventsSuppressedForThisObject        ( 3590 ),
       ds3FrameFormatMismatch                        ( 3600 ),

       waitToRestore               ( 3610 ),
       extremeHighVoltBatteryA     ( 3620 ),
       extremeLowVoltBatteryA      ( 3630 ),
       extremeHighVoltBatteryB     ( 3640 ),
       extremeLowVoltBatteryB      ( 3650 ),
       iosConfigCopyFailed               ( 3660 ),
       iosConfigCopyInProgress               ( 3670 ),

       -- 3660 through 3700 reserverd for R3.3.x releases

       signalingUnableToSetupCircuit        ( 3710 ),
       errorInStartupConfig               ( 3712 ),
       noStartupConfig               ( 3714 ),
       needToSaveRunningConfig               ( 3716 ),
       invalidAlarm               ( 3718 ),
       rsvpHelloFsmToNeighborDown           ( 3720 ),
       securityInvalidLoginUsernameSeeAuditLog               ( 3722 ),
       databaseBackupFailed               ( 3724 ),
       databaseRestoreFailed               ( 3726 ),
       lMPHelloFsmToControlChannelDown      ( 3730 ),
       lMPNeighborDiscoveryHasFailed        ( 3740 ),
       unauthorizedIncomingSignalingRequest ( 3750 ),
       auditLog80PercentFull               ( 3760 ),
       moduleCommunicationFailure               ( 3762 ),
       auditLog100PercentFullOldestRecordsWillBeLost               ( 3764 ),
       standbyDatabaseOutOfSync               ( 3766 ),
       redundantPowerCapabilityLost               ( 3768 ),
       forcedSwitchToPrimaryReference       ( 3770 ),
       forcedSwitchToSecondReference               ( 3780 ),
       forcedSwitchToThirdReference               ( 3790 ),
       forcedSwitchToInternalClock               ( 3800 ),
       industrialHighTemperature               ( 3805 ),

       timSectionTraceIdentifierMismatchFailure ( 4000 ),
       sdhMultiplexSectionAlarmIndicationSignal      ( 4010 ),
       sdhMultiplexSectionRemoteFailureIndication    ( 4020 ),
       sdhHighOrderTraceIdentifierMismatch           ( 4030 ),
       sdhAdministrationUnitAlarmIndicationSignal    ( 4040 ),
       sdhAdministrationUnitLossofPointer            ( 4050 ),
       sdhSLMFHighOrderUnequippedPath                ( 4060 ),
       sdhSLMFHighOrderPathLabelMismatch             ( 4070 ),
       sdhHighOrderRemoteFailureIndication           ( 4080 ),
       sdhTributaryUnitLossofPointer                 ( 4090 ),
       sdhTributaryUnitAlarmIndicationSignal         ( 4100 ),
       sdhSLMFLowOrderUnequippedPath                 ( 4110 ),
       sdhSLMFLowOrderPathLabelMismatch              ( 4120 ),
       sdhLowOrderTraceIdentifierMismatch            ( 4130 ),
       sdhLowOrderRemoteFailureIndication            ( 4140 ),
       g811PrimaryReferenceClockTraceable            ( 4150 ),
       g812TransitNodeClockTraceable                 ( 4160 ),
       g812LocalNodeClockTraceable                   ( 4170 ),
       g813SynchronousEqptTimingSourceTraceable      ( 4180 ),
       loopbackDueToFEACCommandE1                    ( 4190 ),
       loopbackCommandSentToFarEndE1                 ( 4200 ),
       loopbackDueToFEACCommandE3                    ( 4210 ),
       farEndMultipleE1LOSDetectedOnE3               ( 4220 ),
       farEndE1EqptFailNonServiceAffecting           ( 4230 ),
       farEndE1EqptFailServiceAffecting              ( 4240 ),
       farEndSingleE1LOS                             ( 4250 ),
       farEndE3EqptFailServiceAffecting              ( 4260 ),
       loopbackCommandSentToFarEndE3                 ( 4270 ),
       farEndE3EqptFailNonServiceAffecting           ( 4280 ),
       lowVoltBatteryA                               ( 4290 ),
       highVoltBatteryA                              ( 4300 ),
       lowVoltBatteryB                               ( 4310 ),
       highVoltBatteryB                              ( 4320 ),
       msspRingOutOfSync                             ( 4330 ),
       resynchronizedMSSPTables                      ( 4340 ),
       automaticSNCPSwitchCausedByAIS               ( 4350 ),
       automaticSNCPSwitchCausedByLOP               ( 4360 ),
       automaticSNCPSwitchCausedByUneq              ( 4370 ),
       automaticSNCPSwitchCausedByPDI               ( 4380 ),
       automaticSNCPSwitchCausedBySfber             ( 4390 ),
       automaticSNCPSwitchCausedBySdber             ( 4400 ),
       concatenationErrorSTM                         ( 4410 ),
       idleConditionE3                               ( 4420 ),
       channelMSSPInconsistentAPSCode                ( 4430 ),
       channelMSSPImproperAPSCodeAPS                 ( 4440 ),
       channelMSSPNodeIdMismatchAPS                  ( 4450 ),
       channelMSSPDefaultKAPS                        ( 4460 ),
       channelMSSPConnectionLossAPS                  ( 4470 ),
       minimumClockTraceableSDH                      ( 4480 ),
       lineIsInWaitToRestoreStateSDH                 ( 4490 ),
       passedBERThresholdForSignalDegradeHighOrder   ( 4500 ),
       passedBERThresholdForSignalFailHighOrder      ( 4510 ),
       passedBERThresholdForSignalDegradeLowOrder    ( 4520 ),
       passedBERThresholdForSignalFailLowOrder       ( 4530 ),
       failureToSwitchToProtectionHighOrder          ( 4540 ),
       failureToSwitchToProtectionLowOrder           ( 4550 ),
       sdhAdministrationUnitLossOfMultiframe         ( 4560 ),
       sdhSpanIsInWaitToRestoreState                 ( 4570 ),
       a8b10bOutOfSync                               ( 4755 ),
       odukAlarmIndicationSignal                     ( 4760 ),
       otukAlarmIndicationSignal                     ( 4765 ),
       otukSMBackwardDefectIndication                 ( 4770 ),
       fecUncorrectedWord                            ( 4780 ),
       gccTerminationFailure                         ( 4785 ),
       otukIncomingAlignmentError                    ( 4790 ),
       odukLockedDefectPm                            ( 4795 ),
       lossOfMultiFrame                              ( 4800 ),
       odukOpenConnectionIndication                  ( 4805 ),
       payloadTypeIdentifierMismatch                 ( 4810 ),
       odukTrailTraceIdentifierMismatch              ( 4815 ),
       otukTrailTraceIdentifierMismatch              ( 4820 ),
       equipmentHighLaserBias                        ( 4825 ),
       equipmentHighLaserTemp                        ( 4830 ),
       equipmentHighLaserPeltier                     ( 4835 ),
       equipmentHighRxPower                          ( 4840 ),
       equipmentHighTxPower                          ( 4845 ),
       equipmentHighTransceiverVoltage               ( 4850 ),
       equipmentLowLaserBias                         ( 4855 ),
       equipmentLowLaserTemp                         ( 4860 ),
       equipmentLowLaserPeltier                      ( 4865 ),
       equipmentLowRxPower                           ( 4870 ),
       equipmentLowTxPower                           ( 4875 ),
       equipmentLowTransceiverVoltage                ( 4880 ),
       equipmentRxLocked                             ( 4885 ),
       equipmentSquelched                            ( 4890 ),
       equipmentTxLocked                             ( 4895 ),
       otukSignalFailure                              ( 4900 ),
       odukSignalFailure                              ( 4905 ),
       otukSignalDegrade                              ( 4910 ),
       odukSignalDegrade                              ( 4915 ),
       pluggablePortMissing                          ( 4920 ),
       pluggablePortRateMismatch                     ( 4925 ),
       pluggablePortSecurityCodeMismatch             ( 4930 ),
       tciNotSelected                                ( 4935 ),
       tci1ClockFailure                              ( 4940 ),
       odukPMBackwardDefectIndication                 ( 4945 ),
       odukTCM1BackwardDefectIndication               ( 4950 ),
       odukTCM2BackwardDefectIndication               ( 4955 ),
       equipmentHighRxTemperature                    ( 4960 ),
       equipmentLowRxTemperature                     ( 4965 ),
       tci2ClockFailure                              ( 4970 ),
       equipmentWavelengthMismatch                   ( 4975 ),
       dspCommunicationFailure                       ( 4980 ),
       dspFailure                                    ( 4985 ),
       laserApproachingEndOfLife                     ( 5000 ),
       crossconnectLoopback                          ( 5010 ),
       adminLogoutOfUser                             ( 5020 ),
       userLockedOut                                 ( 5030 ),
       adminLockoutOfUser                            ( 5040 ),
       adminLockoutClear                             ( 5050 ),
       invalidLoginUsername                          ( 5060 ),
       invalidLoginPassword                          ( 5070 ),
       invalidLoginLockedOut                         ( 5080 ),
       invalidLoginAlreadyLoggedOn                   ( 5090 ),
       loginOfUser                                   ( 5100 ),
       automaticLogoutOfIdleUser                     ( 5110 ),
       logoutOfUser                                  ( 5120 ),
       enhancedRemoteFailureIndicationPathServer       ( 5200 ),
       enhancedRemoteFailureIndicationPathConnectivity ( 5210 ),
       enhancedRemoteFailureIndicationPathPayload    ( 5220 ),
       firewallHasBeenDisabled                       ( 5230 ),
       securityIntrusionAttemptDetectedSeeAuditLog   ( 5240 ),
       securityIntrusionIncorrectUsername            ( 5250 ),
       connectionEquipmentMismatch                   ( 5260 ),
       disableInactiveUser                           ( 5270 ),
       disableInactiveClear                          ( 5280 ),
       batteryFailure                                ( 5290 ),
       extremeHighVolt                               ( 5300 ),
       extremeLowVolt                                ( 5310 ),
       highVolt                                      ( 5320 ),
       lowVolt                                       ( 5330 ),
       suspendUser                                   ( 5340 ),
       suspendUserClear                              ( 5350 ),
       lineDCCTerminationFailure                     ( 5360 ),
       multiplexSectionDCCTerminationFailure         ( 5370 ),
       gigabitEthernetOutOfSync                      ( 5380 ),
       sequenceMismatch               ( 5390 ),
       lossOfAlignment               ( 5400 ),
       outOfUseAdministrativeCommand               ( 5410 ),
       outOfUseTransportFailure               ( 5420 ),
       vcatGroupDown               ( 5430 ),
       vcatGroupDegraded               ( 5440 ),
       vcatGroupIncomplete               ( 5450 ),
       alarmIndicationSignalInTX                     ( 5460 ),
       remoteAlarmIndicationInTX                     ( 5470 ),
       kbyteChannelFailure               ( 5480 ),
       apsInvalidMode               ( 5490 ),
       ipAddressAlreadyInUseWithinTheSameDCCArea               ( 5500 ),
       nodeNameAlreadyInUseWithinTheSameDCCArea               ( 5510 ),
       rearPanelEthernetLinkRemoved               ( 5520 ),
       manualSwitchToProtectResultedInNoTrafficSwitch               ( 5530 ),
       manualSwitchBackToWorkingResultedInNoTrafficSwitch               ( 5540 ),
       forcedSwitchToProtectionResultedInNoTrafficSwitch               ( 5550 ),
       forcedSwitchBackToWorkingResultedInNoTrafficSwitch               ( 5560 ),
       duplicateSerialNumberDetectedOnAPluggableEntity               ( 5570 ),
       lossOfSignalForOpticalChannel               ( 5600 ),
       encapsulationMismatchPath               ( 5610 ),
       encapsulationMismatchVT               ( 5620 ),
       encapsulationMismatchHighOrderPath               ( 5630 ),
       encapsulationMismatchLowOrderPath               ( 5640 ),
       gfpUserPayloadMismatch               ( 5650 ),
       gfpFibreChannelDistanceExtensionMismatch               ( 5660 ),
       gfpFibreChannelDistanceExtensionBufferStarvation               ( 5670 ),
       fibreChannelDistanceExtensionCreditStarvation               ( 5680 ),
       automaticWDMANSFinished               ( 5690 ),
       gfpClientSignalFailDetected               ( 5700 ),
       gfpLossOfFrameDelineation               ( 5710 ),
       gfpExtensionHeaderMismatch               ( 5730 ),
       lossOfSignalForOverhead               ( 5740 ),
       opticalSafetyRemoteInterlockOn               ( 5750 ),
       automaticPowerControlCorrectionSkipped               ( 5770 ),
       apcCannotSetValueDueToRangeLimits               ( 5780 ),
       lcasVCGMemberTxSideInADDState               ( 5790 ),
       farEndManualSwitchBackToWorkingSpan               ( 5800 ),
       farEndForcedSwitchBackToWorkingSpan               ( 5810 ),
       universalTransponderModuleHardwareFailure               ( 5820 ),
       universalTransponderModuleCommunicationFailure               ( 5830 ),
       pluginModuleRangeSettingsMismatch               ( 5840 ),
       lcasVCGMemberTxSideInDNUState               ( 5850 ),
       lcasControlWordCRCCheckFailure               ( 5860 ),
       lcasVCGMemberRxSideInFAILState               ( 5870 ),
       signalLossOnDataInterface               ( 5880 ),
       synchronizationLossOnDataInterface               ( 5890 ),
       portFAIL               ( 5900 ),
       unreachablePortTargetPower               ( 5910 ),
       portAddPowerDegradeLow               ( 5920 ),
       portAddPowerDegradeHigh               ( 5930 ),
       portAddPowerFailLow               ( 5940 ),
       portAddPowerFailHigh               ( 5950 ),
       automaticPowerControlTerminatedOnManualRequest               ( 6000 ),
       oduk1AlarmIndicationSignal               ( 6010 ),
       oduk2AlarmIndicationSignal               ( 6020 ),
       oduk3AlarmIndicationSignal               ( 6030 ),
       oduk4AlarmIndicationSignal               ( 6040 ),
       temperatureReadingMismatchBetweenSCCards               ( 6050 ),
       voltageReadingMismatchBetweenSCCards               ( 6060 ),
       alarmsSuppressedOnOutOfGroupVCATMember               ( 6070 ),
       blsrSoftwareVersionMismatch               ( 6080 ),
       optimized1Plus1APSPrimaryFacility               ( 6090 ),
       optimized1Plus1APSPrimarySectionMismatch               ( 6100 ),
       optimized1Plus1APSInvalidPrimarySection               ( 6110 ),
       compositeClockHighLineVoltage               ( 6120 ),
       berThresholdExceededForSignalDegradeVT               ( 6130 ),
       berThresholdExceededForSignalFailureVT               ( 6140 ),
       spanLengthOutOfRange               ( 6150 ),
       vtPathTraceIdentifierMismatch               ( 6190 ),
       lossOfFrameInTX               ( 6200 ),
       provisioningMismatch               ( 6210 ),
       sectionTraceIdentifierMismatch               ( 6220 ),
       regeneratorSectionTraceIdentifierMismatch               ( 6230 ),
       switchingMatrixModuleFailureWorking               ( 6240 ),
       switchingMatrixModuleFailureProtect               ( 6250 ),
       slotCommunicationDisabled               ( 6260 ),
       sessionTimeLimitExpired               ( 6270 ),
       userPasswordChangeRequired               ( 6280 ),
       isisAdjacencyFailure               ( 6290 ),
       msspSoftwareVersionMismatch               ( 6300 ),
       remoteAuthenticationFailSeeAuditLog               ( 6310 ),
       ringIsSquelchingSTSTraffic               ( 6330 ),
       ringIsSquelchingVTTraffic               ( 6340 ),
       archivalOfAuditLogFailed               ( 6350 ),
       rprWrapped               ( 6360 ),
       shelfCommunicationFailure               ( 6370 ),
       duplicatedShelfIdentifier               ( 6380 ),
       softwareMismatch               ( 6390 ),
       lmpFailure               ( 6400 ),
       opticalTerminationIncomplete               ( 6410 ),
       forwardDefectIndication               ( 6420 ),
       payloadMissingIndication               ( 6430 ),
       spanLossNotChecked               ( 6440 ),
       ringIsSquelchingHigherOrderTraffic               ( 6450 ),
       ringIsSquelchingLowerOrderTraffic               ( 6460 ),
       badPacketCountExceedsThreshold               ( 6470 ),
       linkLayerKeepAliveFailure               ( 6480 ),
       autonegotiationRemoteFailureIndication               ( 6490 ),
       trailSignalFail               ( 6500 ),
       ds1LoopbackCommandSentToFarEnd               ( 6510 ),
       multiplexSectionSignalDegraded               ( 6520 ),
       multiplexSectionExcessiveErrors               ( 6530 ),
       highOrderPathSignalDegraded               ( 6540 ),
       highOrderPathExcessiveErrors               ( 6550 ),
       lowOrderPathSignalDegraded               ( 6560 ),
       lowOrderPathExcessiveErrors               ( 6570 ),
       regeneratorSectionDCCTerminationFailure               ( 6580 ),
       networkMemoryPoolLow               ( 6590 ),
       ospfRoutingTableOverflow               ( 6600 ),
       autoLaserShutdownDisabled               ( 6610 ),
       rprProtectionIsActive               ( 6630 ),
       maxRPRStationNumberExceeded               ( 6640 ),
       rprProtectionConfigurationMismatched               ( 6650 ),
       reservedBandwidthLinkRateExceededOnRinglet0               ( 6660 ),
       reservedBandwidthLinkRateExceededOnRinglet1               ( 6670 ),
       rprInterfaceInPassThroughMode               ( 6680 ),
       rprPeerNodeIsMissing               ( 6690 ),
       rprRIFailure               ( 6700 ),
       rprSignalFailure               ( 6710 ),
       rprSignalDegrade               ( 6720 ),
       rprSpanMismatch               ( 6750 ),
       workQueueFull                 ( 6980 ),
       equipmentPowerFailureAtConnectorA               ( 7000 ),
       equipmentPowerFailureAtConnectorB               ( 7005 ),
       equipmentPowerFailureAtReturnConnectorA               ( 7010 ),
       equipmentPowerFailureAtReturnConnectorB               ( 7015 ),
       bridgeAndRollHasOccurred                      ( 7055 ),
       bridgeAndRollIsPendingAValidSignal            ( 7060 ), 
       clockBusFailureShelfControllerA               ( 7160 ),
       clockBusFailureShelfControllerB               ( 7165 ),
       ospfHelloFail               ( 7185 ),
       openIOSlots               ( 7200 ),
       lossOfClockFromMateShelfController               ( 7210 ),
       odukAlarmIndicationSignalTCM1                 ( 13100 ),
       odukAlarmIndicationSignalTCM2                 ( 13105 ),
       odukLockedDefectTCM1                          ( 13110 ),
       odukLockedDefectTCM2                          ( 13115 ),
       otukLossOfFrame                               ( 13120 ),
       odukOpenConnectionIndicationTCM1              ( 13125 ),
       odukOpenConnectionIndicationTCM2              ( 13130 ),
       odukTrailTraceIdentifierMismatchTCM1          ( 13135 ),
       odukTrailTraceIdentifierMismatchTCM2          ( 13140 ),
       odukSignalFailureTCM1                         ( 13145 ),
       odukSignalFailureTCM2                         ( 13150 ),
       odukSignalDegradeTCM1                         ( 13155 ),
       odukSignalDegradeTCM2                         ( 13160 ),
       lossOfChannel                                 ( 13165 ),
       fecMismatch                                   ( 13170 ),
       timSectionMonitorTraceIdentifierMismatchFailure ( 13175 ),
       automaticLaserShutdown                        ( 13180 ),
       shutterInsertionLossVariationDegradeLow       ( 13200 ),
       opticalChannelDeactivationFailure             ( 13205 ),
       shutterInsertionLossVariationDegradeHigh      ( 13210 ),
       networkTopologyIncomplete                     ( 13215 ),
       pluginModuleCommunicationFailure              ( 13220 ),
       opticalNetworkTypeMismatch                    ( 13225 ),
       laserPowerDegradeLow                          ( 13230 ),
       automaticPowerControlFailure                  ( 13235 ),
       opticalPowerDegradeHigh                       ( 13240 ),
       automaticPowerControlDisabled                 ( 13245 ),
       opticalPowerFailureLow                        ( 13250 ),
       ringIdMismatch                                ( 13255 ),
       opticalPowerFailureHigh                       ( 13260 ),
       lossOfContinuity                              ( 13270 ),
       variableOpticalAttenuatorDegradeLow           ( 13280 ),
       variableOpticalAttenuatorDegradeHigh          ( 13290 ),
       variableOpticalAttenuatorFailureLow           ( 13300 ),
       variableOpticalAttenuatorFailureHigh          ( 13310 ),
       laserBiasDegrade                              ( 13320 ),
       laserBiasFailure                              ( 13330 ),
       laserTemperatureDegrade                       ( 13340 ),
       opticalAmplifierGainDegradeLow                ( 13350 ),
       opticalAmplifierGainDegradeHigh               ( 13360 ),
       opticalAmplifierGainFailureLow                ( 13370 ),
       opticalAmplifierGainFailureHigh               ( 13380 ),
       opticalChannelConnectionFailure               ( 13390 ),
       opticalChannelIncomplete                      ( 13395 ),
       opticalChannelActivationFailure               ( 13400 ),
       laserAutoPowerReduction                       ( 13410 ),
       caseTemperatureDegrade                        ( 13420 ),
       fiberTemperatureDegrade                       ( 13430 ),
       shutterFailure                                ( 13440 ),
       awgTemperatureDegrade                         ( 13450 ),
       awgTemperatureFailure                         ( 13460 ),
       awgOverTemperature                            ( 13470 ),
       opticalAmplifierInitialization                ( 13480 ),
       awgWarmUp                                     ( 13490 ),
       incomingSignalLossOnFibreChannelInterface               ( 13510 ),
       incomingSynchronizationLossOnFibreChannelInterface               ( 13515 ),
       outOfFrameDetectedByGFPReceiver               ( 13520 ),
       clientSignalLossFramesDetectedByGFPReceiver               ( 13525 ),
       clientSychronizationLossFramesDetectedByGFPReceiver               ( 13530 )
}

-- Cerent454ObjectType ::= TEXTUAL-CONVENTION
--    DISPLAY-HINT "d"
--    STATUS current
--    DESCRIPTION
--        "Very similar to the alarm type TC, except this is
--         used for object type display"
--    SYNTAX INTEGER {
--     objectNone            (   1 ),
--     objectEntity          (  10 ),
--     objectInterface       (  20 ),
--     objectOspf            (  30 ),
--     objectProtectionGroup (  40 ),
--     objectSdccTerm        (  50 ),
--     objectSync            (  60 ),
--     objectSecurity        (  70 ),
--     objectTopologyElement (  80 ),
--     objectSystem          (  90 ),
--     objectStsConnection   ( 100 ),
--     objectVtConnection    ( 110 ),
--     objectSonetPool       ( 120 ),
--     objectEtherBridge     ( 130 ),
--     objectSpanningTree    ( 140 ),
--     objectVlan            ( 150 ),
--     objectCircuit         ( 160 )
--    }

Cerent454EntityClass ::= TEXTUAL-CONVENTION
   -- DISPLAY-HINT "d"
   STATUS current
   DESCRIPTION
       "This is the TC used to find out to which cerent454EntityClass
        an alarm belongs to."
   SYNTAX INTEGER {
  unknownEntity   (  1 ),
  ne              ( 10 ),
  backplane       ( 30 ),
  eqpt            ( 50 ),
  port            ( 60 ),
  ocn             ( 70 ),
  stmn            ( 71 ),
  aip             ( 80 ),
  fanTray         ( 90 ),
  crs             ( 100 ),
  ds3             ( 110 ),
  almExpPanel     ( 120 ),
  almIfExtnsn     ( 130 ),
  stsMon          ( 140 ),
  vcMonHp         ( 141 ),
  dwdmClient      ( 150 ),
  stsTerm         ( 160 ),
  vcTermHp        ( 161 ),
  dwdmTrunk       ( 170 ),
  dwdmOptics      ( 180 ),
  psSts           ( 190 ),
  rsms            ( 200 ),
  xcSts           ( 210 ),
  bits            ( 220 ),
  dwdmFec         ( 230 ),
  neSynchRef      ( 240 ),
  dwdm8b10b       ( 250 ),
  extSynchRef     ( 260 ),
  dwdmOtn         ( 270 ),
  envAlrm         ( 280 ),
  envCtrl         ( 290 ),
  neRing          ( 360 ),
  ds1             ( 390 ),
  vtMon           ( 410 ),
  vcMonLp         ( 411 ),
  vtTerm          ( 420 ),
  vcTermLP        ( 421 ),
  fUdc            ( 430 ),
  msUdc           ( 440 ),
  spareSdcc       ( 450 ),
  ucpCircuit      ( 480 ),
  ucpIpcc         ( 490 ),
  ucpNeighbor     ( 500 ),
  ec1             ( 510 ),
  ps              ( 520 ),
  psVt            ( 530 ),
  e100t           ( 540 ),
  e1000t          ( 550 ),
  etherBridge     ( 560 ),
  e1              ( 600 ),
  e3              ( 630 ),
  e4              ( 640 ),
  stm1E           ( 650 ),
  ds3i            ( 660 ),
  g1000           ( 670 ),
  ml100t          ( 680 ),
  ml1000          ( 690 ),
  dwdmSfp         ( 700 ),
  dwdmScl         ( 710 ),
  dwdmTcm1        ( 720 ),
  dwdmTcm2        ( 730 ),
  dwdmOcn         ( 740 ),
  dwdmSm          ( 750 ),
  dwdmPm          ( 760 ),
  dwdmTcm         ( 770 ),
  pwr             ( 780 ),
  stsTermVcat     ( 790 ),
  vtTermVcat      ( 800 ),
  vcatGroup       ( 810 ),
  fcmr            ( 820 ),
  entOptics       ( 830 ),
  ce100t          ( 840 ),
  ppm             ( 850 ),
  twor            ( 860 ),
  isc             ( 870 ),
  escon           ( 880 ),
  bic             ( 890 ),
  gfp             ( 900 ),
  gige            ( 910 ),
  pos             ( 920 ),
  cap             ( 930 ),
  dwdmData        ( 940 ),
  logFac          ( 950 ),
  ge              ( 960 ),
  fc              ( 970 ),
  ec1p1           ( 980 ),
  mlFx            ( 990 ),
  ochTerm          ( 1000 ),
  shelf          ( 1010 ),
  ce1000          ( 1020 ),
  lmp          ( 1040 ),
  lmpControlChannel          ( 1050 ),
  lmpTeLink          ( 1060 ),
  lmpDataLink          ( 1070 ),
  rpr          ( 1080 ),
  aots           ( 3200 ),
  ots            ( 3210 ),
  oms            ( 3220 ),
  och            ( 3230 ),
  osc            ( 3240 ),
  ochnc          ( 3250 )
}

-- **************************************************************
cerent454Objects OBJECT-IDENTITY
      STATUS      current
      DESCRIPTION
            "The cerent454 specific objects themselves"
      ::= { cerent454Mib 20 }

-- **************************************************************
-- All Cisco OTBU generic objects definitions
-- These will be available for all Cisco OTBU products. Hence
-- they are defined once under generic category.

cerent454CommonObjectsGroup OBJECT-IDENTITY
      STATUS      current
      DESCRIPTION
            "The group to combine all the Cisco OTBU common
             objects"
      ::= { cerentCommonObjects 10 }

cerent454EnableNotification   OBJECT-TYPE
       SYNTAX      TruthValue
       MAX-ACCESS  read-write
       STATUS      current
       DESCRIPTION
               "This variable indicates whether the system produces
                notifications.  A value=FALSE will prevent notifications
                from being sent by this system."
       DEFVAL { true }
       ::= { cerent454CommonObjectsGroup 10 }

cerent454NodeTime OBJECT-TYPE
       SYNTAX       DisplayString
       MAX-ACCESS   read-only
       STATUS current
       DESCRIPTION
       "Indicates current local time as reflected by
        the Cisco OTBU equipment. The format this scalar is
        YYYYMMDDhhmmss{S/D}. E.g.,
        20011103133453D means 1:34:53 PM PDT on 03/Nov/2001
        19990614095436S means 9:54:36 AM PST on 14/Jun/1999.
        If the last octet is S then the time is standard time.
        Otherwise it is D to indicate it is daylight saving
        time, if applicable"
       ::= { cerent454CommonObjectsGroup 20 }

cerent454SentNotifications OBJECT-TYPE
       SYNTAX      Counter32
       MAX-ACCESS read-only
       STATUS current
       DESCRIPTION
              "A count of v1+v2 notifications sent out
               by the agent. Resets to zero after
               cold/warm start."
       ::= { cerent454CommonObjectsGroup 30 }

cerent454LastChangeTime OBJECT-TYPE
    SYNTAX      TimeStamp
    MAX-ACCESS  read-only
    STATUS      current
    DESCRIPTION
            "The value of sysUpTime at the time
             a conceptual row is created or deleted
             in cerent454AlarmTable "
    ::= { cerent454CommonObjectsGroup 40 }

-- **************************************************************
--
cerent454GeneralGroup OBJECT-IDENTITY
       STATUS       current
       DESCRIPTION
              ""
       ::= { cerent454Objects 20 }

cerent454SoftwareVersion OBJECT-TYPE
       SYNTAX       DisplayString
       MAX-ACCESS   read-only
       STATUS current
       DESCRIPTION
       "Indicates the version of software that is
        used in Cisco ONS 15454. E.g., 2.2.03"
       ::= { cerent454GeneralGroup 10 }

cerent454AlarmGroup OBJECT-IDENTITY
       STATUS       current
       DESCRIPTION
              "The group that will represent all the
               alarm info in the Cisco ONS 15454 node"
       ::= { cerent454Objects 30 }

cerent454AlarmCount       OBJECT-TYPE
       SYNTAX       Unsigned32
       MAX-ACCESS   read-only
       STATUS current
       DESCRIPTION
           "Total number of active alarms in Cisco ONS 15454.
            This equals the total number of rows in
            cerent454AlarmTable at any time."
       ::= { cerent454AlarmGroup 10 }

cerent454AlarmTable       OBJECT-TYPE
       SYNTAX SEQUENCE OF Cerent454AlarmEntry
       MAX-ACCESS not-accessible
       STATUS current
       DESCRIPTION
              "This table holds all the current raised
               alarms.  When an alarm is raised, it will
               appear a new entry in the table.
               Whenever an alarm is cleared it will be
               removed from the table and all the entries
               from below will be moved up by another row."
       ::= { cerent454AlarmGroup 20 }

cerent454AlarmEntry       OBJECT-TYPE
       SYNTAX Cerent454AlarmEntry
       MAX-ACCESS not-accessible
       STATUS current
       DESCRIPTION
              "Row definition for cerent454AlarmTable"
       INDEX { cerent454AlarmIndex, cerent454AlarmType }
       ::= { cerent454AlarmTable 1 }

Cerent454AlarmEntry ::= SEQUENCE {
       cerent454AlarmIndex           Integer32,
       cerent454AlarmObjectType      Cerent454EntityClass,
       cerent454AlarmSlotNumber      Integer32,
       cerent454AlarmPortNumber      CerentPortNumber,
       cerent454AlarmLineNumber      Integer32,
       cerent454AlarmObjectIndex     Integer32,
       cerent454AlarmType            Cerent454AlarmType,
       cerent454AlarmState           CerentNotificationClass,
       cerent454AlarmTimeStamp       TimeStamp,
       cerent454AlarmObjectName      DisplayString,
       cerent454AlarmAdditionalInfo  DisplayString
       }

cerent454AlarmIndex       OBJECT-TYPE
       SYNTAX Integer32 ( 1..2147483647 ) -- all +ve values
       MAX-ACCESS not-accessible
       STATUS current
       DESCRIPTION
              "Identifies each entry in alarm table.
               May not start with one and there may be some
               missing numbers."
       ::= { cerent454AlarmEntry 10 }

cerent454AlarmObjectType       OBJECT-TYPE
       SYNTAX Cerent454EntityClass
       MAX-ACCESS read-only
       STATUS current
       DESCRIPTION
              "This will indicate what is the type
               of the entity which raised this alarm.
               ( E.g., DS3, etherBridge, VT-TERM, etc )
               The NMS is expected to use this value
               to decide which table to poll for
               further info about the alarm"
       ::= { cerent454AlarmEntry 20 }

cerent454AlarmSlotNumber           OBJECT-TYPE
       SYNTAX Integer32
       MAX-ACCESS read-only
       STATUS current
       DESCRIPTION
              "This will indicate what is the slot
               of the object which raised this alarm.
               If not relevant to the alarm, will be
               zero."
       ::= { cerent454AlarmEntry 30 }

cerent454AlarmPortNumber          OBJECT-TYPE
       SYNTAX CerentPortNumber
       MAX-ACCESS read-only
       STATUS current
       DESCRIPTION
              "This will indicate what is the port
               of the object which raised this alarm."
       ::= { cerent454AlarmEntry 40 }

cerent454AlarmLineNumber           OBJECT-TYPE
       SYNTAX Integer32
       MAX-ACCESS read-only
       STATUS current
       DESCRIPTION
              "This will indicate what is the port
               of the object which raised this alarm.
               If not relevant to the alarm, will be
               zero."
       ::= { cerent454AlarmEntry 50 }

cerent454AlarmObjectIndex       OBJECT-TYPE
       SYNTAX Integer32
       MAX-ACCESS read-only
       STATUS current
       DESCRIPTION
              "Every alarm is raised by an object and
               this object is an entry in a specific
               table. This is the index of the object
               in that table E.g., if the alarm is interface
               related, this index is the index of the
               interface in the interface table."
       ::= { cerent454AlarmEntry 60 }

cerent454AlarmType       OBJECT-TYPE
       SYNTAX Cerent454AlarmType
       MAX-ACCESS read-only
       STATUS current
       DESCRIPTION
              "Indicates what the exact nature of the
               alarm. See the Cerent454AlarmType TC
               for mapping details "
       ::= {cerent454AlarmEntry  70 }

cerent454AlarmState OBJECT-TYPE
       SYNTAX        CerentNotificationClass
       MAX-ACCESS read-only
       STATUS current
       DESCRIPTION
              "Specifies alarm severity and service 
               affecting status ( SA/NSA ). Only 
               {minor|major|critical}+{NA|NSA} alarms and
               standing conditions will be represented here.

               However, this mib object is included in each
               trap dispatched and in the trap this object 
               can contain all the possible values of
               CerentNotificationClass type."
       ::= { cerent454AlarmEntry 80 }

cerent454AlarmTimeStamp OBJECT-TYPE
       SYNTAX   TimeStamp
       MAX-ACCESS read-only
       STATUS current
       DESCRIPTION
              "The value of sysUpTime when this entry was
               created. This is accurate only upto a second."
       ::= { cerent454AlarmEntry 90 }

cerent454AlarmObjectName OBJECT-TYPE
       SYNTAX  DisplayString 
       MAX-ACCESS read-only
       STATUS current
       DESCRIPTION
              "TL1-style user-visible name which uniquely
               identifies an object in the system"
       ::= { cerent454AlarmEntry 100 }

cerent454AlarmAdditionalInfo OBJECT-TYPE
       SYNTAX  DisplayString 
       MAX-ACCESS read-only
       STATUS current
       DESCRIPTION
              "Additional information for the alarm object.
              In the current version of the MIB, this object 
              contains the following information :-
              
              a) Provisioned description for alarms of type
              'failureDetectedExternalToTheNE'.

              This object would be a null string if no 
              additional information is specified."
       ::= { cerent454AlarmEntry 110 }
       
--  All Cisco ONS 15454 Threshold definitions.

cerent454ThresholdGroup OBJECT-IDENTITY
       STATUS       current
       DESCRIPTION
              "The group that will represent all the
               threshold info in the Cisco ONS 15454 node"
       ::= { cerent454Objects 40 }

cerent454ThresholdTable       OBJECT-TYPE
       SYNTAX SEQUENCE OF Cerent454ThresholdEntry
       MAX-ACCESS not-accessible
       STATUS current
       DESCRIPTION
              "This table holds all the defined
               Thresholds.

               This table is currently unimplemented."

       ::= { cerent454ThresholdGroup 10 }

cerent454ThresholdEntry       OBJECT-TYPE
       SYNTAX Cerent454ThresholdEntry
       MAX-ACCESS not-accessible
       STATUS current
       DESCRIPTION
              "Row definition for cerent454ThresholdTable"
       INDEX { cerent454ThresholdIndex }
       ::= { cerent454ThresholdTable 1 }

Cerent454ThresholdEntry ::= SEQUENCE {
      cerent454ThresholdIndex           Integer32,
      cerent454ThresholdMonitorType     CerentMonitorType,
      cerent454ThresholdLocation        CerentLocation,
      cerent454ThresholdPeriod          CerentPeriod,
      cerent454ThresholdSetValue        Integer32,
      cerent454ThresholdCurrentValue    Integer32,
      cerent454ThresholdDetectType      INTEGER
    }

cerent454ThresholdIndex  OBJECT-TYPE
       SYNTAX  Integer32 (1..2147483647) -- Same as IfIndex from IF-MIB
       MAX-ACCESS not-accessible
       STATUS current
       DESCRIPTION
              "Uniquely identifies each entry in Threshold table.
               May not start with one and there will be some
               missing numbers."
       ::= { cerent454ThresholdEntry 10 }

cerent454ThresholdMonitorType  OBJECT-TYPE
       SYNTAX                  CerentMonitorType
       MAX-ACCESS read-only
       STATUS current
       DESCRIPTION
       "This object indicates the type of metric monitored."
       ::= { cerent454ThresholdEntry 20 }

cerent454ThresholdLocation     OBJECT-TYPE
       SYNTAX                  CerentLocation
       MAX-ACCESS read-only
       STATUS current
       DESCRIPTION
       "This indicates if it near or far end"
       ::= { cerent454ThresholdEntry 30 }

cerent454ThresholdPeriod       OBJECT-TYPE
       SYNTAX                  CerentPeriod
       MAX-ACCESS read-only
       STATUS current
       DESCRIPTION
       "The sampling interval period is indicated here"
       ::= { cerent454ThresholdEntry 40 }

cerent454ThresholdSetValue     OBJECT-TYPE
       SYNTAX                  Integer32
       MAX-ACCESS read-only
       STATUS current
       DESCRIPTION
       "The value of this object will be threshold that was 
        provisioned by the NMS"
       ::= { cerent454ThresholdEntry 50 }

cerent454ThresholdCurrentValue OBJECT-TYPE
       SYNTAX                  Integer32
       MAX-ACCESS read-only
       STATUS current
       DESCRIPTION
       "The current value of the counter which 
        measures the metric. This column will never be
        implemented as the value of this object is already
        accessible through IETF MIBs."
       ::= { cerent454ThresholdEntry 60 }

cerent454ThresholdDetectType  OBJECT-TYPE
       SYNTAX  INTEGER {
                  unknown(1),
                  none(10),
                  mon(20),
                  term(30) 
                  }
       MAX-ACCESS read-only
       STATUS current
       DESCRIPTION
       "The value of this object will be the detect type for the
        threshold."
       ::= { cerent454ThresholdEntry 70 }
       

--  All Cisco ONS 15454 Notifications definitions.

cerent454Events OBJECT-IDENTITY
      STATUS      current
      DESCRIPTION
            "Place holder for all notifications of Cisco ONS 15454"
      ::= { cerent454Mib 30 }

cerent454V2Events OBJECT-IDENTITY
      STATUS      current
      DESCRIPTION
                 "The sub-identifier has to be zero, as part
                  of the interoperability agreement between
                  SNMPv1 and SNMPv2 worlds."
      ::= { cerent454Events 0  }

-- ---------------------------------------------
-- All the Cisco ONS 15454 notifications definitions
-- ---------------------------------------------

-- object and event groups

alarmUnknown
  NOTIFICATION-TYPE
    OBJECTS {
        cerent454NodeTime,
        cerent454AlarmState,
        cerent454AlarmObjectType,
        cerent454AlarmObjectIndex,
        cerent454AlarmSlotNumber,
        cerent454AlarmPortNumber,
        cerent454AlarmLineNumber,
        cerent454AlarmObjectName
    }
    STATUS current
    DESCRIPTION "alarm unknown"
    --#SUMMARY "%d Object:%d Index:%d Slot:%d Port:%d AID:%s"
    --#ARGUMENTS {$2, $3, $4, $5, $6, $8}
    --#GENERIC 6
    --#SOURCE_ID "A"
    --#TIMEINDEX 0

    ::= { cerent454V2Events  1 }

alarmCutoffIsInManualMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "alarm cutoff is in manual mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 10 }

failureDetectedExternalToTheNE
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName,
      cerent454AlarmAdditionalInfo
    }
    STATUS current
    DESCRIPTION "failure detected External to the NE"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 20 }

externalError
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "external error"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 30 }

excessiveSwitching
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "excessive switching"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 40 }

sdccTerminationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDCC Termination failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 50 }

incomingFailureCondition
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "incoming failure condition"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 60 }

alarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "alarm indication signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 70 }

alarmIndicationSignalLine
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "alarm indication signal LINE"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 80 }

alarmIndicationSignalPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "alarm indication signal Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 90 }

alarmIndicationSignalVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "alarm indication signal VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 100 }

channelFailureAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel failure APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 110 }

channelByteFailureAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel Byte failure APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 120 }

channelProtectionSwitchingChannelMatchFailureAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel Protection Switching Channel Match failure APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 130 }

channelAutomaticProtectionSwitchModeMismatchAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel Automatic Protection Switch Mode Mismatch APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 140 }

channelFarEndProtectionLineFailureAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel far end protection line failure APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 150 }

inconsistentAPSCode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Inconsistent APS code"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 160 }

improperAPSCode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Improper APS code"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 170 }

nodeIdMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Node Id Mismatch APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 180 }

channelDefaultKAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel Default K APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 190 }

connectionLoss
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Connection loss APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 200 }

bipolarViolation
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "bipolar Violation"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 210 }

carrierLossOnTheLAN
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "carrier Loss on the LAN"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 220 }

concatenationErrorSTS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "concatenation error STS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 230 }

excessCollisionsOnTheLAN
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "excess collisions on the LAN"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 240 }

facilityCriticalAlarmCausedByDS3FacilityFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility critical alarm caused by DS3 facility failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 250 }

farEndAIS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end AIS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 260 }

farEndMultipleDS1LOSDetectedOnDS3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end Multiple DS1 LOS detected on DS3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 270 }

farEndDS1EqptFailNonServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end DS1 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 280 }

farEndDS1EqptFailServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end DS1 Eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 290 }

farEndSingleDS1LOS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end Single DS1 LOS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 300 }

farEndDS3EqptFailNonServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end DS3 Eqpt failure non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 310 }

farEndDS3EqptFailServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end DS3 Eqpt failure service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 320 }

farEndCommonEquipmentFailureNonServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end common Eqpt failure non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 330 }

farEndIDLE
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end IDLE"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 340 }

farEndLOS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end LOS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 350 }

farEndLOF
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end LOF"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 360 }

farEndBlockError
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far End Block Error"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 370 }

ds3IdleCondition
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "idle Condition DS3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 380 }

lossOfFrame
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loss of Frame"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 390 }

lossOfPointer
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loss of Pointer"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 400 }

lossOfPointerPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loss of Pointer Path "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 410 }

lossOfPointerVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loss of Pointer VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 420 }

lossOfSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loss of Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 430 }

outOfFrame
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "out of Frame"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 440 }

pathSelectorInabilityToSwitchToAValidSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "path Selector inability to swtich to a valid signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 450 }

remoteAlarmIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Alarm Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 460 }

remoteFailureIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Failure Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 470 }

remoteFailureIndicationLine
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Failure Indication LINE"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 480 }

remoteFailureIndicationPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Failure Indication Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 490 }

remoteFailureIndicationVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Failure Indication VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 500 }

signalDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility has passed BER Threshold for Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 510 }

severelyErroredFrame
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "severely Errored Frame"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 520 }

signalFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility has passed BER threshold for Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 530 }

signalLabelMismatchFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "signal Label Mismatch Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 540 }

payloadDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Payload Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 550 }

payloadDefectIndicationPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Payload Defect Indication - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 560 }

payloadLabelMismatchPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Payload Label Mismatch - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 570 }

signalLabelMismatchFailurePayloadLabelMismatchVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "signal Label Mismatch Failure Payload Label Mismatch VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 580 }

unequippedPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Unequipped - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 590 }

signalLabelMismatchFailureUnequippedVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "signal Label Mismatch Failure Unequipped VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 600 }

lossOfSynchronization
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 610 }

outOfSynchronization
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Out of Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 620 }

primarySynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Primary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 630 }

secondarySynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Secondary Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 640 }

thirdSynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Third Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 650 }

fourthSynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Fourth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 660 }

fifthSynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Fifth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 670 }

sixthSynchronizationReferenceFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Sixth Synchronization Reference Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 680 }

failedToReceiveSynchronizationStatusMessage
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failed to receive Synchronization Status Message"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 690 }

synchronizationStatusMessagesAreDisabledOnThisInterface
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "synchronization Status Messages are disabled on this
interface"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 700 }

primaryReferenceSourceStratum1Traceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "primary Reference Source Stratum 1 Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 710 }

synchronizedTraceabilityUnknown
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "synchronized Traceability Unknown"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 720 }

stratum2Traceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "stratum 2 Traceable "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 730 }

transitNodeClockTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "transit Node clock Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 740 }

stratum3ETraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "stratum 3E Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 750 }

stratum3Traceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "stratum 3 Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 760 }

sonetMinimumClockTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SONET Minimum Clock Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 770 }

stratum4Traceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "stratum 4 Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 780 }

doNotUseForSynchronization
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "do not Use for Synchronization"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 790 }

reservedForNetworkSynchronizationUse
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "reserved for Network Synchronization Use"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 800 }

outgoingFailureCondition
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "outgoing failure condition"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 810 }

remoteDefectIndicationLine
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Defect Indication LINE"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 820 }

remoteDefectIndicationPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "remote Defect Indication Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 830 }

freeRunningSynchronizationMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "free Running Synchronization mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 840 }

holdoverSynchronizationMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "holdover synchronization mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 850 }

fastStartSynchronizationMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "fast Start synchronization mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 860 }

internalHardwareFaultOrFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "internal hardware fault or failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 870 }

errorInternalToTheNEDetected
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "error Internal to the NE Detected"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 880 }

internalMessageError
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "internal Message Error"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 890 }

mismatchOfEquipmentAndAttributes
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "mismatch of Equipment and Attributes"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 900 }

watchdogTimerTimeout
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "watchdog Timer Timeout"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 910 }

softwareFaultOrFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "software Fault or failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 920 }

softwareFaultDataIntegrityFault
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "software Fault -  Data integrity fault :
                 The newly added provisioning or hardware has
                 caused the database to grow beyond its limit.
                 That is, the newly added object(s) in the system
                 has(have) enough memory to exist onboard but
                 too large to be saved in the database."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 930 }

programFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "program failure "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 940 }

controlEquipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 950 }

controlEquipmentPrimaryNonVolatileBackupMemoryFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Primary non volatile Backup Memory
failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 960 }

cntrlEqptSecondaryNonVolatileBackupMemoryFailed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Secondary non volatile Backup Memory
failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 970 }

controlEquipmentControlBusFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Control Bus failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 980 }

controlEquipmentControlBus1Failure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Control Bus 1 failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 990 }

controlEquipmentControlBus2Failure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Control Bus 2 failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1000 }

communicationFailureTCCAToShelfSLOT1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1010 }

communicationFailureTCCAToShelfSLOT2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1020 }

communicationFailureTCCAToShelfSLOT3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1030 }

communicationFailureTCCAToShelfSLOT4
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 4"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1040 }

communicationFailureTCCAToShelfSLOT5
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 5"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1050 }

communicationFailureTCCAToShelfSLOT6
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 6"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1060 }

communicationFailureTCCAToShelfSLOT7
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 7 "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1070 }

communicationFailureTCCAToShelfSLOT8
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 8"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1080 }

communicationFailureTCCAToShelfSLOT9
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 9"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1090 }

communicationFailureTCCAToShelfSLOT10
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 10"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1100 }

communicationFailureTCCAToShelfSLOT11
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 11"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1110 }

communicationFailureTCCAToShelfSLOT12
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 12"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1120 }

communicationFailureTCCAToShelfSLOT13
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 13"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1130 }

communicationFailureTCCAToShelfSLOT14
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 14"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1140 }

communicationFailureTCCAToShelfSLOT15
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 15"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1150 }

communicationFailureTCCAToShelfSLOT16
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 16"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1160 }

communicationFailureTCCAToShelfSLOT17
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to Shelf SLOT 17 "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1170 }

tccAToDCCAProcessorCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC A to DCC A processor"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1180 }

communicationFailureTCCBToShelfSLOT1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 1 "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1190 }

communicationFailureTCCBToShelfSLOT2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1200 }

communicationFailureTCCBToShelfSLOT3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1210 }

communicationFailureTCCBToShelfSLOT4
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 4"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1220 }

communicationFailureTCCBToShelfSLOT5
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 5"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1230 }

communicationFailureTCCBToShelfSLOT6
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 6"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1240 }

communicationFailureTCCBToShelfSLOT7
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 7"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1250 }

communicationFailureTCCBToShelfSLOT8
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 8"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1260 }

communicationFailureTCCBToShelfSLOT9
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 9"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1270 }

communicationFailureTCCBToShelfSLOT10
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 10"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1280 }

communicationFailureTCCBToShelfSLOT11
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 11"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1290 }

communicationFailureTCCBToShelfSLOT12
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 12"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1300 }

communicationFailureTCCBToShelfSLOT13
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 13"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1310 }

communicationFailureTCCBToShelfSLOT14
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 14"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1320 }

communicationFailureTCCBToShelfSLOT15
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 15"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1330 }

communicationFailureTCCBToShelfSLOT16
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 16"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1340 }

communicationFailureTCCBToShelfSLOT17
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCC B to Shelf SLOT 17"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1350 }

communicationFailureTCCPBToTCCJBprocessor
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "communication failure TCCP B to TCCJ A processor"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1360 }

controlEquipmentControlCommunicationsEquipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Control Communications equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1370 }

controlEquipmentControlProcessorFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Control processor failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1380 }

controlEquipmentWorkingMemoryFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "control Equipment Working memory failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1390 }

interconnectionEquipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1400 }

interconnectionEquipmentFailurePayloadBus1Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 1 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1410 }

interconnectionEquipmentFailurePayloadBus2Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 2 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1420 }

interconnectionEquipmentFailurePayloadBus3Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 3 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1430 }

interconnectionEquipmentFailurePayloadBus4Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 4 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1440 }

interconnectionEquipmentFailurePayloadBus5Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 5 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1450 }

interconnectionEquipmentFailurePayloadBus6Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 6 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1460 }

interconnectionEquipmentFailurePayloadBus7Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 7 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1470 }

interconnectionEquipmentFailurePayloadBus8Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 8 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1480 }

interconnectionEquipmentFailurePayloadBus9Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 9 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1490 }

interconnectionEquipmentFailurePayloadBus10Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 10 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1500 }

interconnectionEquipmentFailurePayloadBus11Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 11 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1510 }

interconnectionEquipmentFailurePayloadBus12Working
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 12 Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1520 }

interconnectionEquipmentFailurePayloadBus1Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 1 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1530 }

interconnectionEquipmentFailurePayloadBus2Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 2 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1540 }

interconnectionEquipmentFailurePayloadBus3Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 3 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1550 }

interconnectionEquipmentFailurePayloadBus4Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 4 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1560 }

interconnectionEquipmentFailurePayloadBus5Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 5 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1570 }

interconnectionEquipmentFailurePayloadBus6Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 6 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1580 }

interconnectionEquipmentFailurePayloadBus7Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 7 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1590 }

interconnectionEquipmentFailurePayloadBus8Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 8 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1600 }

interconnectionEquipmentFailurePayloadBus9Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 9 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1610 }

interconnectionEquipmentFailurePayloadBus10Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 10 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1620 }

interconnectionEquipmentFailurePayloadBus11Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 11 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1630 }

interconnectionEquipmentFailurePayloadBus12Protect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Equipment failure Payload Bus 12 Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1640 }

interconnectionEqptTimeSlotInterchangeEqptFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "interconnection Eqpt Time slot interchange eqpt failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1650 }

equipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1660 }

highTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1670 }

equipmentFailureInvalidMACAddress
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment failure Invalid MAC Address"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1680 }

equipmentFailureBoardFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment failure Board Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1690 }

diagnosticFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment failure Diagnostics Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1700 }

equipmentFailureMediumAccessControl
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment failure Medium Access Control"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1710 }

facilityTerminationEquipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility Termination equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1720 }

automaticLaserShutoffDueToHighTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Laser Shutoff Due To High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1730 }

failureToReleaseFromProtection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure To Release from protection"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1740 }

facilityTerminationEquipmentReceiverFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility Termination equipment Receiver failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1750 }

facilityTerminationEquipmentTransmitFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility Termination equipment Transmit failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1760 }

facilityTerminationEquipmentReceiverMissing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility Termination equipment Receiver missing"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1770 }

facilityTerminationEquipmentTransmitterMissing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "facility Termination equipment Transmitter missing"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1780 }

failureToSwitchToProtection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure To Switch to protection"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1790 }

failureToSwitchToProtectionRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure To Switch to protection Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1800 }

failureToSwitchToProtectionSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure To Switch to protection Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1810 }

failureToSwitchToProtectionPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure to Switch to protection Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1820 }

failureOfCoolingFanTray
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "failure of cooling fan tray"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1830 }

equipmentUnitPlugIn
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment unit plug in"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1840 }

nePowerFailureAtConnector
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "NE power failure detected at connector"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1850 }

powerFailureFuseAlarm
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "power failure Fuse Alarm"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1860 }

synchronizationUnitFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "synchronization unit failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1870 }

synchronizationSwitchingEquipmentFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "synchronization switching Equipment failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1880 }

equipmentUnitUnplug
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "equipment unit un plug"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1890 }

loopback
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loop back"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1900 }

loopbackDueToFEACCommandDS1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback due to FEAC command DS1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1910 }

loopbackCommandSentToFarEndDS1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback Command sent to Far End DS1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1920 }

ds3LoopbackDueToFEACCommand
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback due to FEAC command DS3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1930 }

loopbackCommandSentToFarEndDS3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback Command sent to Far End DS3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1940 }

loopbackDueToFarEndCommandDS2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback due to Far End Command DS2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1950 }

loopbackCommandSentToFarEndDS2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback Command sent to Far End DS2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1960 }

loopbackFacility
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loop back facility"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1970 }

loopbackNetwork
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loop back Network"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1980 }

loopbackTerminal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loop back Terminal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 1990 }

manuallyCausedAbnormalCondition
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manually caused abnormal condition"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2000 }

newRootDiscoveredInBridgedNetwork
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "new Root discovered in bridged network"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2010 }

topologyChangeDiscoveredInBridgedNetwork
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "topology change discovered in bridged network"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2020 }

normalCondition
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "normal condition"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2030 }

embeddedOperationsChannelFailureLinkDown
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "embedded Operations Channel failure link down"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2040 }

peerStateMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "peer state mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2050 }

proceduralError
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "procedural Error"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2060 }

improperRemoval
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Improper Removal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2070 }

duplicateNodeID
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Duplicate Node ID"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2080 }

blsrOutOfSync
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BLSR out of sync"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2090 }

resynchronizedBLSRTables
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BLSR tables resynchronized"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2100 }

protectionUnitNotAvailable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "protection unit not available"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2110 }

performanceMonitorThresholdCrossingAlert
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName,
      cerent454ThresholdMonitorType,
      cerent454ThresholdLocation,
      cerent454ThresholdPeriod,
      cerent454ThresholdSetValue,
      cerent454ThresholdCurrentValue,
      cerent454ThresholdDetectType
    }
    STATUS current
    DESCRIPTION "performance Monitor Threshold Crossing Alert"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2120 }

occurrenceOfAProtectionSwitchingEvent
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "occurrence of a protection switching event"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2130 }

recoveryOrServiceProtectionActionHasBeenInitiated
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "recovery or service protection action has been initiated"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2140 }

automaticSystemReset
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic system Reset"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2150 }

automaticUPSRSwitchCausedByAIS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by AIS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2160 }

automaticUPSRSwitchCausedByLOP
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by Lop"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2170 }

automaticUPSRSwitchCausedByUneq
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by Uneq"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2180 }

automaticUPSRSwitchCausedByPDI
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by PDI"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2190 }

automaticUPSRSwitchCausedBySfber
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by Sfber"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2200 }

automaticUPSRSwitchCausedBySdber
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic UPSR switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2210 }

coldRestart
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "cold Restart"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2220 }

workingFacilityOrEqptForcedSwitchedToWorking
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched to working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2230 }

workingFacilityOrEqptForcedSwitchedToWorkingRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched to working Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2240 }

workingFacilityOrEqptForcedSwitchedToWorkingSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched to working Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2250 }

workingFacilityOrEqptForcedSwitchedProtectionUnit
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched protection unit"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2260 }

workingFacilityOrEqptForcedSwitchedProtectionUnitRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched protection unit
Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2270 }

workingFacilityOrEqptForcedSwitchedProtectionUnitSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched protection unit
Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2280 }

workingFacilityOrEqptForcedSwitchedProtectionUnitPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt forced switched protection unit
Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2290 }

initializationInitiated
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "initialization initiated"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2300 }

lockoutOfProtection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of Protection"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2310 }

lockoutOfProtectionRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of Protection Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2320 }

lockoutOfProtectionSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of Protection Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2330 }

lockoutOfProtectionPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of Protection Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2340 }

lockoutOfWorking
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2350 }

lockoutOfWorkingRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of working Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2360 }

lockoutOfWorkingSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "lockout of working Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2370 }

manualSystemReset
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manual system Reset"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2380 }

manualSwitchToInternalClock
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch to Internal Clock"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2390 }

manualSwitchToPrimaryReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Primary Reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2400 }

manualSwitchToSecondReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Second Reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2410 }

manualSwitchToThirdReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Third reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2420 }

manualSwitchToFourthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Fourth reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2430 }

manualSwitchToFifthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Fifth reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2440 }

manualSwitchToSixthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Sixth reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2450 }

manualSwitchOfWorkingFacilityOrEqptToProtectionRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manualSwitch of working facility or eqpt to protection
Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2460 }

manualSwitchOfWorkingFacilityOrEqptToProtectionSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manualSwitch of working facility or eqpt to protection
Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2470 }

manualSwitchOfWorkingFacilityOrEqptToProtection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manualSwitch of working facility or eqpt to protection"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2480 }

manualSwitchOfWorkingFacilityOrEqptToProtectionUnit
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manualSwitch of Working facility or eqpt to Protection
unit"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2490 }

workingFacilityOrEqptManualSwitchToProtectionUnitRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt manualSwitch to Protection unit
Ring"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2500 }

workingFacilityOrEqptManualSwitchToProtectionUnitSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "working facility or eqpt manualSwitch to Protection unit
Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2510 }

manualSwitchOfWorkingFacilityOrEqptToProtectionPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "manualSwitch of working facility or eqpt to Protection
Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2520 }

powerFailureRestart
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Powerfail Restart"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2530 }

ringIsSquelchingTraffic
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ring is squelching traffic"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2540 }

softwareDownloadInProgress
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "software download in progress"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2550 }

switchToInternalClock
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Internal clock"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2560 }

switchToPrimaryReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Primary refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2570 }

switchToSecondReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Second refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2580 }

switchToThirdReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Third refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2590 }

switchToFourthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Fourth refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2600 }

switchToFifthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Fifth refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2610 }

switchToSixthReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switch To Sixth refernce"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2620 }

systemReboot
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "system reboot"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2630 }

switchedBackToWorking
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switched Back To Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2640 }

switchedToProtection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switched To Protection"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2650 }

warmRestart
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "warm Restart"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2660 }

ringIsInWaitToRestoreState
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2670 }

manualSwitchRequest
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch Request"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2680 }

forcedSwitchRequest
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch Request"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2690 }

lockoutSwitchRequest
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Lockout Switch Request"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2700 }

rmonHistoriesAndAlarmsReset
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RMON histories and alarms have been reset due to chipset
reboot"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2710 }

rmonThresholdCrossingAlarm
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
   }
   STATUS current
    DESCRIPTION "Crossing of Falling/Rising Threshold detected"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2720 }

alarmsSuppressedByUserCommand
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Alarms Suppressed By User Command"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2730 }

alarmsSuppressedForMaintenance
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Alarms Suppressed For Maintenance"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2740 }

switchingMatrixModuleFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switching Matrix Module Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2750 }

lanConnectionPolarityReversed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Lan Connection Polarity Reversed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2760 }

autonomousPerformanceMonitoringReportMessageInhibited
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Autonomous Performance Monitoring Report Message Inhibited"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2780 }

ioSlotToXCONCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "IO Slot To XCON Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2790 }

stsPathTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "STS Path Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2800 }

nodePowerFailureAtConnectorA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "NE power failure at connector A"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2810 }

nodePowerFailureAtConnectorB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "NE power failure at connector B"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2820 }

freeMemoryOnCardVeryLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Free memory on the card is very low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2830 }

freeMemoryOnCardNearZero  
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Free memory on the card is near zero"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2840 }

exerciseRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2850 }

exerciseSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2860 }

squelchingPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Squelching Path"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2870 }

extraTrafficPreempted
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extra Traffic Preempted."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2880 }

farEndLockoutOfWorkingRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Lockout of working - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2890 }

farEndLockoutOfWorkingSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Lockout of working - Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2900 }

farEndLockoutOfProtectionRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Lockout of Protection - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2910 }

farEndLockoutOfProtectionAllSpans
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2920 }

farEndWorkingFacilityForcedToSwitchToProtectionUnitRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Working facility forced to switch to protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2930 }


farEndWorkingFacilityForcedToSwitchToProtectionUnitSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Working facility forced to switch to protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2940 }

farEndManualSwitchOfWorkingFacilityToProtectionUnitRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Manual Switch of Working facility to Protection unit - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2950 }

farEndManualSwitchOfWorkingFacilityToProtectionUnitSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Manual Switch of Working facility to Protection unit - Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2960 }

farEndExerciseRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Exercise Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2970 }

farEndExerciseSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Exercise Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2980 }

farEndBERThresholdPassedForSignalFailureRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End BER threshold passed for Signal Failure - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 2990 }

farEndBERThresholdPassedForSignalFailureSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End BER threshold passed for Signal Failure - Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3000 }

farEndBERThresholdPassedForSignalDegradeRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End BER threshold passed for Signal Degrade - Ring."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3010 }

farEndBERThresholdPassedForSignalDegradeSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End BER threshold passed for Signal Degrade - Span."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3020 }

channelFarEndProtectionLineSignalDegradeAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "APS Channel - Far End Protection Line Signal Degrade."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3030 }

ringSwitchIsActiveOnTheEastSide
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3040 }


ringSwitchIsActiveOnTheWestSide
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3050 }

spanSwitchIsActiveOnTheEastSide
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Span Switch is active on the East Side."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3060 }

spanSwitchIsActiveOnTheWestSide
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Span Switch is active on the West Side."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3070 }

uniDirectionalFullPassThroughIsActive
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Uni-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3080 }


biDirectionalFullPassThroughIsActive
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Bi-directional Full Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3090 }

kBytePassThroughIsActive
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "K Bytes Pass Through is active."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3100 }

ringIsSegmented
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring is Segmented."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3110 }

ringTopologyIsUnderConstruction
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Topology is under construction."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3120 }

lockoutOfProtectionAllSpans
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Lockout of Protection - All Spans."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3130 }

farEndOfFiberIsProvisionedWithDifferentRingID
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far end of fiber is provisioned with different ring ID"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3140 }

bothEndsOfFiberProvisionedAsEastOrBothAsWest
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Both ends of fiber provisioned as East, or both as West"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3150 }

securityInvalidLoginUsernameSeeAuditTrail
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS deprecated
    DESCRIPTION "Security: invalid login (see Audit Trail)"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3160 }

autonomousMessagesInhibited
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Autonomous messages inhibited"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3170 }

trafficStormLANtemporarilyDisabled
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Traffic storm on LAN. LAN temporarily disabled."

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3180 }

tl1ReptDbchgMessagesInhibited
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "REPT^DBCHG messages of TL1 inhibited"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3190 }

userIdHasExpired
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Security: user ID has expired"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3200 }

partialFanFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Partial Fan Failure"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3210 }

forceSwitchRequestOnRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Force switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3220 }

forceSwitchRequestOnSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Force switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3230 }

lockoutSwitchRequestOnRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Lockout switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3240 }

lockoutSwitchRequestOnSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Lockout switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3250 }

manualSwitchRequestOnRing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual switch request on Ring"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3260 }

manualSwitchRequestOnSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual switch request on Span"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3270 }

communicationFailurePeerToPeerSlotControlBusA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Peer to Peer Slot communication failure - Control Bus A"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3280 }

communicationFailurePeerToPeerSlotControlBusB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Peer to Peer Slot communication failure - Control Bus B"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3290 }

controllerAToShelfSlotCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Controller A to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3300 }

controllerBToShelfSlotCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Controller B to shelf slot communication failure"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3310 }

interconnectionEquipmentFailureWorkingPayloadBus
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Interconnection Equipment Failure - Working Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3320 }

interconnectionEquipmentFailureProtectPayloadBus
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Interconnection Equipment Failure - Protect Payload Bus"

    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3330 }

inhibitSwitchToProtectRequestOnEquipment
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Inhibit Switch to Protect Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3340 }

inhibitSwitchToWorkingRequestOnEquipment
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Inhibit Switch to Working Request on equipment"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3350 }

berThresholdExceededForSignalDegradeLine
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Degrade - Line"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3360 }

berThresholdExceededForSignalDegradePath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Degrade - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3370 }

berThresholdExceededForSignalFailureLine
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold Exceeded For Signal Failure - Line"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3380 }

berThresholdExceededForSignalFailurePath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold Exceeded For Signal Failure - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3390 }

exerciseRingCompleted
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Ring completed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3400}

exerciseSpanCompleted
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Span completed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3410}

spanIsInWaitToRestoreState
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3420 }

exerciseRingFailed
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Ring Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3430 }

exerciseSpanFailed
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Exercise Span Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3440 }

farEndLockoutOfProtectionChannelInSpan
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far end Lockout of Protection Channel-Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3450 }

manufacturingEepromFailure
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manufacturing EEPROM Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3460 }

replaceableEquipmentIsMissing
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Replaceable Equipment/Unit Is Missing"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3470 }

softwareDownloadFailed
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Software Download Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3480 }

extraTrafficDropped
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extra Traffic Dropped"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3490 }

pktLossDueToOversubscribedXmit 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "pkt loss due to oversubscribed xmit"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3500 }

pktLossDueToOversubscribedRcv   
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "pkt loss due to oversubscribed rcv"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3510 }

excessiveEthernetFlowCtlXmited  
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "excessive ethernet flow ctl xmited"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3520 }

excessiveEthernetFlowCtlRecvd   
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "excessive ethernet flow ctl recvd"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3530 }

transportLayerFailure   
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "transport layer failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3540 }

etherHdgeInternalFifoUnderrun   
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "HDGE internal fifo underrun"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3550 }

synchronizationReferenceFrequencyOutOfBounds
    NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Synchronization reference frequency out of bounds."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3560 }

ntpOrSntpHostFailure
    NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "NTP/SNTP Host Failure."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3570 }

peerCardNotResponding
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Peer Card Not Responding"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3580 }

alarmsAndEventsSuppressedForThisObject
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Alarms and events suppressed for this object"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3590 }

ds3FrameFormatMismatch
    NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "DS3 Frame Format Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3600 }

waitToRestore
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Wait To Restore"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3610 }

extremeHighVoltBatteryA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme High Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3620 }

extremeLowVoltBatteryA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme Low Volt Battery A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3630 }

extremeHighVoltBatteryB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme High Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3640 }

extremeLowVoltBatteryB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme Low Volt Battery B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3650 }

iosConfigCopyFailed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "IOS config copy failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3660 }

iosConfigCopyInProgress
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "IOS config copy in progress"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3670 }

-- Begin: UCP traps

signalingUnableToSetupCircuit
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Signaling Unable to setup circuit"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3710 }

errorInStartupConfig
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Error in Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3712 }

noStartupConfig
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "No Startup Config"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3714 }

needToSaveRunningConfig
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Need to Save Running Config"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3716 }

invalidAlarm
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Invalid Alarm"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3718 }

rsvpHelloFsmToNeighborDown
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RSVP Hello FSM to Neighbor down"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3720 }

securityInvalidLoginUsernameSeeAuditLog
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Security: Invalid Login - Username - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3722 }

databaseBackupFailed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Database Backup Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3724 }

databaseRestoreFailed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Database Restore Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3726 }

lMPHelloFsmToControlChannelDown
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LMP Hello FSM to Control Channel down"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3730 }

lMPNeighborDiscoveryHasFailed
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LMP Neighbor Discovery has failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3740 }

unauthorizedIncomingSignalingRequest
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Unauthorized incoming signaling request"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3750 }

auditLog80PercentFull
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Audit Log 80 Percent Full"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3760 }

moduleCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3762 }

auditLog100PercentFullOldestRecordsWillBeLost
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Audit Log 100 Percent Full - Oldest records will be lost"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3764 }

standbyDatabaseOutOfSync
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Standby Database Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3766 }

redundantPowerCapabilityLost
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Redundant Power Capability Lost"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3768 }

-- End: UCP traps

forcedSwitchToPrimaryReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch To Primary Reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3770 }

forcedSwitchToSecondReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch To Second Reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3780 }

forcedSwitchToThirdReference
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch To Third Reference"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3790 }

forcedSwitchToInternalClock
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch To Internal Clock"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3800 }

industrialHighTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Industrial High Temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 3805 }


-- Begin: SDH Traps

timSectionTraceIdentifierMismatchFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "TIM Section - Trace Identifier Mismatch Failure."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4000 }

sdhMultiplexSectionAlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Multiplex Section - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4010 }

sdhMultiplexSectionRemoteFailureIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Multiplex Section - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4020 }

sdhHighOrderTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH High Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4030 }

sdhAdministrationUnitAlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Administration Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4040 }

sdhAdministrationUnitLossofPointer
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Administration Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4050 }

sdhSLMFHighOrderUnequippedPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH SLMF High Order - Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4060 }

sdhSLMFHighOrderPathLabelMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH SLMF High Order - Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4070 }

sdhHighOrderRemoteFailureIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH High Order - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4080 }

sdhTributaryUnitLossofPointer
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Tributary Unit - Loss of Pointer."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4090 }

sdhTributaryUnitAlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Tributary Unit - Alarm Indication Signal."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4100 }

sdhSLMFLowOrderUnequippedPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Low Order - SLMF Unequipped Path."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4110 }

sdhSLMFLowOrderPathLabelMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Low Order - SLMF Path Label Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4120 }

sdhLowOrderTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Low Order - Trace Identifier Mismatch."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4130 }

sdhLowOrderRemoteFailureIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Low Order - Remote Failure Indication."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4140 }

g811PrimaryReferenceClockTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "G811 - Primary Reference Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4150 }

g812TransitNodeClockTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "G812 - Transit Node Clock traceable." 
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4160 }

g812LocalNodeClockTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "G812 - Local Node Clock traceable."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4170 }

g813SynchronousEqptTimingSourceTraceable
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "G813 - Synchronous Equipment Timing Source traceable."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4180 }

loopbackDueToFEACCommandE1  
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback due to FEAC Command E1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4190 }

loopbackCommandSentToFarEndE1 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback Command sent to Far End E1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4200 }
 
loopbackDueToFEACCommandE3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback due to FEAC Command E3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4210 }

farEndMultipleE1LOSDetectedOnE3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end Multiple E1 LOS detected on E3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4220 }

farEndE1EqptFailNonServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end E1 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4230 }

farEndE1EqptFailServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end E1 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4240 }
  
farEndSingleE1LOS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end Single E1 LOS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4250 }

farEndE3EqptFailServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end E3 eqpt fail service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4260 }
 
loopbackCommandSentToFarEndE3 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "loopback Command sent to Far End E3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4270 }

farEndE3EqptFailNonServiceAffecting
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "far end E3 eqpt fail non service affecting"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4280 }

lowVoltBatteryA 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Low Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4290 }

highVoltBatteryA                 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Volt - Battery A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4300 }

lowVoltBatteryB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Low Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4310 }
 
highVoltBatteryB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Volt - Battery B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4320 }
 
msspRingOutOfSync
NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "MS-SP ring out of sync"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4330 }

resynchronizedMSSPTables    
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "MS-SP ring tables resynchronized"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4340 }
              
automaticSNCPSwitchCausedByAIS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by AIS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4350 }
 
automaticSNCPSwitchCausedByLOP
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by Lop"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4360 }
    
automaticSNCPSwitchCausedByUneq
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by Uneq"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4370 }
  
automaticSNCPSwitchCausedByPDI 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by PDI"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4380 }

automaticSNCPSwitchCausedBySfber  
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by Sfber"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4390 }

automaticSNCPSwitchCausedBySdber
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "automatic SNCP switch caused by Sdber"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4400 }

concatenationErrorSTM
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "concatenation error STM"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4410 }

idleConditionE3
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "idle Condition E3"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4420 }

channelMSSPInconsistentAPSCode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel MSSP inconsistent APS code"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4430 }


channelMSSPImproperAPSCodeAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel MSSP Improper APS code APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4440 }

channelMSSPNodeIdMismatchAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel MSSP Node Id Mismatch APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4450 }

channelMSSPDefaultKAPS
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel MSSP Default K APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4460 }

channelMSSPConnectionLossAPS  
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "channel MSSP Connection loss APS"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4470 }

minimumClockTraceableSDH
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Minimum clock Traceable"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4480 }

lineIsInWaitToRestoreStateSDH
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH line is in Wait To Restore state "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4490 }

passedBERThresholdForSignalDegradeHighOrder
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Degrade - High Order"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4500 }

passedBERThresholdForSignalFailHighOrder
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Failure - High Order"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4510 }

passedBERThresholdForSignalDegradeLowOrder
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Degrade - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4520 }

passedBERThresholdForSignalFailLowOrder
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold exceeded for Signal Failure - Low Order"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4530 }

failureToSwitchToProtectionHighOrder 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Failure To Switch To Protection - High Order Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4540 }

failureToSwitchToProtectionLowOrder 
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Failure To Switch To Protection - Low Order Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4550 }
    
sdhAdministrationUnitLossOfMultiframe
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH Administration Unit Loss of Multiframe."
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4560 }

sdhSpanIsInWaitToRestoreState
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "SDH span is in Wait To Restore state"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4570 }

-- End: SDH Traps

a8b10bOutOfSync
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "8B10B Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4755 }

odukAlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4760 }

otukAlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUk: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4765 }

otukSMBackwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUk: Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4770 }

odukBackwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4775 }

fecUncorrectedWord
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "FEC Uncorrected Word"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4780 }

gccTerminationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4785 }

otukIncomingAlignmentError
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUk: Incoming Alignment Error"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4790 }

odukLockedDefectPm
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: Locked Defect PM"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4795 }

lossOfMultiFrame
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Multi-Frame"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4800 }

odukOpenConnectionIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: Open Connection Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4805 }

payloadTypeIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Payload Type Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4810 }

odukTrailTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4815 }

otukTrailTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUk: Trail Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4820 }

equipmentHighLaserBias
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4825 }

equipmentHighLaserTemp
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4830 }

equipmentHighLaserPeltier
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Laser Peltier"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4835 }

equipmentHighRxPower
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Rx power"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4840 }

equipmentHighTxPower
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Tx power"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4845 }

equipmentHighTransceiverVoltage
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4850 }

equipmentLowLaserBias
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Laser Bias"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4855 }

equipmentLowLaserTemp
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Laser Temp"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4860 }

equipmentLowLaserPeltier
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Laser Peltier "
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4865 }

equipmentLowRxPower
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Rx power"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4870 }

equipmentLowTxPower
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Tx power"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4875 }

equipmentLowTransceiverVoltage
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Transceiver voltage"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4880 }

equipmentRxLocked
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Rx Locked"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4885 }

equipmentSquelched
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Squelched"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4890 }

equipmentTxLocked
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Tx Locked"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4895 }

otukSignalFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4900 }

odukSignalFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUK Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4905 }

otukSignalDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4910 }

odukSignalDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUK Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4915 }

pluggablePortMissing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Pluggable Port missing"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4920 }

pluggablePortRateMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Pluggable Port rate mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4925 }

pluggablePortSecurityCodeMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Pluggable Port security code mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4930 }

tciNotSelected
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Tci not selected"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4935 }

tci1ClockFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Tci 1 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4940 }

odukPMBackwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: PM Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4945 }

odukTCM1BackwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: TCM1 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4950 }

odukTCM2BackwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk: TCM2 Backward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4955 }

equipmentHighRxTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment High Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4960 }

equipmentLowRxTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Low Rx temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4965 }

tci2ClockFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Tci 2 Clock Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4970 }

equipmentWavelengthMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment Wavelength Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4975 }

dspCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "DSP Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4980 }

dspFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "DSP Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 4985 }


laserApproachingEndOfLife
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Laser Approaching End of Life"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5000 }

crossconnectLoopback
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Cross-connect Loopback"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5010 }

adminLogoutOfUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Admin Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5020 }

userLockedOut
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "User Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5030 }

adminLockoutOfUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Admin Lockout of User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5040 }

adminLockoutClear
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Admin Lockout Clear"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5050 }

invalidLoginUsername
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Invalid Login: Username"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5060 }

invalidLoginPassword
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Invalid Login: Password"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5070 }

invalidLoginLockedOut
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Invalid Login: Locked Out"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5080 }

invalidLoginAlreadyLoggedOn
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Invalid Login - Already Logged On"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5090 }

loginOfUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Login of User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5100 }

automaticLogoutOfIdleUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Logout of IdleUser"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5110 }

logoutOfUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Logout of User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5120 }

enhancedRemoteFailureIndicationPathServer
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Enhanced Remote Failure Indication - Path - Server"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5200 }


enhancedRemoteFailureIndicationPathConnectivity
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Enhanced Remote Failure Indication - Path - Connectivity"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5210 }

enhancedRemoteFailureIndicationPathPayload
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Enhanced Remote Failure Indication - Path - Payload"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5220 }

firewallHasBeenDisabled
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Firewall Has Been Disabled"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5230 }

securityIntrusionAttemptDetectedSeeAuditLog
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Security Intrusion - Incorrect Password"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5240 }

securityIntrusionIncorrectUsername
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Security Intrusion - Incorrect Username"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5250 }
connectionEquipmentMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Connection Equipment Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5260 }

disableInactiveUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Disable Inactive User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5270 }

disableInactiveClear
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Disable Inactive Clear"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5280 }


batteryFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Battery Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5290 }

extremeHighVolt
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme High Volt"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5300 }

extremeLowVolt
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Extreme Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5310 }

highVolt
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Volt"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5320 }

lowVolt
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Low Volt"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5330 }

suspendUser
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Suspend User"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5340 }

suspendUserClear
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Suspend User Clear"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5350 }


lineDCCTerminationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Line DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5360 }

multiplexSectionDCCTerminationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Multiplex Section DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5370 }

gigabitEthernetOutOfSync
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GigaBit Ethernet Out of Sync"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5380 }

sequenceMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Sequence Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5390 }

lossOfAlignment
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Alignment"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5400 }

outOfUseAdministrativeCommand
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Out of Use - Administrative Command"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5410 }

outOfUseTransportFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Out of Use - Transport Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5420 }

vcatGroupDown
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "VCAT Group Down"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5430 }

vcatGroupDegraded
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "VCAT Group Degraded"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5440 }

vcatGroupIncomplete
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "VCAT Group Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5450 }

alarmIndicationSignalInTX
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Alarm Indication Signal in TX"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5460 }

remoteAlarmIndicationInTX
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Remote Alarm Indication in TX"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5470 }

kbyteChannelFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Kbyte Channel Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5480 }

apsInvalidMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "APS Invalid Mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5490 }

ipAddressAlreadyInUseWithinTheSameDCCArea
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "IP address already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5500 }

nodeNameAlreadyInUseWithinTheSameDCCArea
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Node name already in use within the same DCC Area"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5510 }

rearPanelEthernetLinkRemoved
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Rear Panel Ethernet Link Removed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5520 }

manualSwitchToProtectResultedInNoTrafficSwitch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch To Protect Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5530 }

manualSwitchBackToWorkingResultedInNoTrafficSwitch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Manual Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5540 }

forcedSwitchToProtectionResultedInNoTrafficSwitch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch To Protection Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5550 }

forcedSwitchBackToWorkingResultedInNoTrafficSwitch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forced Switch Back To Working Resulted in No Traffic Switch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5560 }

duplicateSerialNumberDetectedOnAPluggableEntity
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Duplicate Serial number detected on a pluggable entity"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5570 }

lossOfSignalForOpticalChannel
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Incoming Payload Signal Absent"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5600 }

encapsulationMismatchPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Encapsulation Mismatch Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5610 }

encapsulationMismatchVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Encapsulation Mismatch - VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5620 }

encapsulationMismatchHighOrderPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Encapsulation Mismatch High Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5630 }

encapsulationMismatchLowOrderPath
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Encapsulation Mismatch Low Order - Path"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5640 }

gfpUserPayloadMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP User Payload Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5650 }

gfpFibreChannelDistanceExtensionMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP Fibre Channel Distance Extension Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5660 }

gfpFibreChannelDistanceExtensionBufferStarvation
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP Fibre Channel Distance Extension Buffer Starvation"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5670 }

fibreChannelDistanceExtensionCreditStarvation
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Fibre Channel Distance Extension Credit Starvation"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5680 }

automaticWDMANSFinished
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic WDM ANS Finished"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5690 }
    
gfpClientSignalFailDetected
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP Client Signal Fail Detected"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5700 }

gfpLossOfFrameDelineation
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP Loss of Frame Delineation"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5710 }

gfpExtensionHeaderMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "GFP Extension Header Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5730 }

lossOfSignalForOverhead
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Signal for Overhead"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5740 }

opticalSafetyRemoteInterlockOn
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Safety Remote Interlock On"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5750 }

automaticPowerControlCorrectionSkipped
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Power Control Correction Skipped"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5770 }

apcCannotSetValueDueToRangeLimits
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "APC cannot set value due to range limits"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5780 }

lcasVCGMemberTxSideInADDState
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LCAS VCG Member Tx Side In ADD State"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5790 }

farEndManualSwitchBackToWorkingSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Manual Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5800 }

farEndForcedSwitchBackToWorkingSpan
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Far End Forced Switch Back to Working - Span"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5810 }

universalTransponderModuleHardwareFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Universal Transponder Module Hardware Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5820 }

universalTransponderModuleCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Universal Transponder Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5830 }

pluginModuleRangeSettingsMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Plug-in Module Range Settings Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5840 }
    
lcasVCGMemberTxSideInDNUState
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LCAS VCG Member Tx Side In DNU State"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5850 }

lcasControlWordCRCCheckFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LCAS Control Word CRC Check Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5860 }

lcasVCGMemberRxSideInFAILState
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LCAS VCG Member Rx Side In FAIL State"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5870 }

signalLossOnDataInterface
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Signal Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5880 }

synchronizationLossOnDataInterface
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Synchronization Loss on Data Interface"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5890 }

portFAIL
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "PORT FAIL"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5900 }

unreachablePortTargetPower
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Unreachable port target power"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5910 }

portAddPowerDegradeLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Port Add Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5920 }

portAddPowerDegradeHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Port Add Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5930 }

portAddPowerFailLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Port Add Power Fail Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5940 }

portAddPowerFailHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Port Add Power Fail High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 5950 }

automaticPowerControlTerminatedOnManualRequest
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Power Control Terminated on Manual request"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6000 }

oduk1AlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk-1: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6010 }

oduk2AlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk-2: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6020 }

oduk3AlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk-3: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6030 }

oduk4AlarmIndicationSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk-4: Alarm Indication Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6040 }

temperatureReadingMismatchBetweenSCCards
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Temperature Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6050 }

voltageReadingMismatchBetweenSCCards
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Voltage Reading Mismatch Between SC Cards"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6060 }

alarmsSuppressedOnOutOfGroupVCATMember
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Alarms Suppressed on Out-Of-Group VCAT Member"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6070 }

blsrSoftwareVersionMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BLSR Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6080 }

optimized1Plus1APSPrimaryFacility
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optimized 1+1 APS Primary Facility"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6090 }

optimized1Plus1APSPrimarySectionMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optimized 1+1 APS Primary Section Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6100 }

optimized1Plus1APSInvalidPrimarySection
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optimized 1+1 APS Invalid Primary Section"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6110 }

compositeClockHighLineVoltage
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Composite Clock High Line Voltage"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6120 }

berThresholdExceededForSignalDegradeVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold Exceeded For Signal Degrade - VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6130 }

berThresholdExceededForSignalFailureVT
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "BER Threshold Exceeded For Signal Failure - VT"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6140 }

spanLengthOutOfRange
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Span Length Out of Range"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6150 }

vtPathTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "VT Path Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6190 }

lossOfFrameInTX
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Frame in TX"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6200 }

provisioningMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Provisioning Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6210 }

sectionTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6220 }

regeneratorSectionTraceIdentifierMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Regenerator Section Trace Identifier Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6230 }

switchingMatrixModuleFailureWorking
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switching Matrix Module Failure - Working"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6240 }

switchingMatrixModuleFailureProtect
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Switching Matrix Module Failure - Protect"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6250 }

slotCommunicationDisabled
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Slot Communication Disabled"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6260 }

sessionTimeLimitExpired
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Session Time Limit Expired"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6270 }

userPasswordChangeRequired
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "User Password Change Required"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6280 }

isisAdjacencyFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ISIS Adjacency Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6290 }

msspSoftwareVersionMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "MSSP Software Version Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6300 }

remoteAuthenticationFailSeeAuditLog
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Remote Authentication Fail - See Audit Log"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6310 }

ringIsSquelchingSTSTraffic
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Is Squelching STS Traffic"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6330 }

ringIsSquelchingVTTraffic
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Is Squelching VT Traffic"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6340 }

archivalOfAuditLogFailed
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Archival of Audit Log Failed"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6350 }

rprWrapped
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Wrapped"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6360 }

shelfCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Shelf Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6370 }

duplicatedShelfIdentifier
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Duplicated Shelf Identifier"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6380 }

softwareMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Software Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6390 }

lmpFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "LMP Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6400 }

opticalTerminationIncomplete
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Termination Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6410 }

forwardDefectIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Forward Defect Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6420 }

payloadMissingIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Payload Missing Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6430 }

spanLossNotChecked
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Span loss not checked"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6440 }

ringIsSquelchingHigherOrderTraffic
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Is Squelching Higher Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6450 }

ringIsSquelchingLowerOrderTraffic
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Is Squelching Lower Order Traffic"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6460 }

badPacketCountExceedsThreshold
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Bad Packet Count Exceeds Threshold"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6470 }

linkLayerKeepAliveFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Link Layer Keep-Alive Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6480 }

autonegotiationRemoteFailureIndication
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Auto-Negotiation Remote Failure Indication"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6490 }

trailSignalFail
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Trail Signal Fail"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6500 }

ds1LoopbackCommandSentToFarEnd
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "DS1 Loopback Command Sent To Far End"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6510 }

multiplexSectionSignalDegraded
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Multiplex Section - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6520 }

multiplexSectionExcessiveErrors
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Multiplex Section - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6530 }

highOrderPathSignalDegraded
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6540 }

highOrderPathExcessiveErrors
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "High Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6550 }

lowOrderPathSignalDegraded
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Low Order Path - Signal Degraded"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6560 }

lowOrderPathExcessiveErrors
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Low Order Path - Excessive Errors"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6570 }

regeneratorSectionDCCTerminationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Regenerator Section - DCC Termination Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6580 }

networkMemoryPoolLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Network Memory Pool Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6590 }

ospfRoutingTableOverflow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OSPF Routing Table Overflow"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6600 }

autoLaserShutdownDisabled
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Auto Laser Shutdown Disabled"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6610 }

rprProtectionIsActive
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Protection Is Active"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6630 }

maxRPRStationNumberExceeded
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Max RPR Station Number Exceeded"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6640 }

rprProtectionConfigurationMismatched
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Protection Configuration Mismatched"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6650 }

reservedBandwidthLinkRateExceededOnRinglet0
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Reserved Bandwidth Link Rate Exceeded On Ringlet0"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6660 }

reservedBandwidthLinkRateExceededOnRinglet1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Reserved Bandwidth Link Rate Exceeded On Ringlet1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6670 }

rprInterfaceInPassThroughMode
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Interface In Pass Through Mode"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6680 }

rprPeerNodeIsMissing
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Peer Node is Missing"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6690 }

rprRIFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR RI Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6700 }

rprSignalFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Signal Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6710 }

rprSignalDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Signal Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6720 }

rprSpanMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "RPR Span Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6750 }

workQueueFull
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Work Queue Full"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 6980 }

equipmentPowerFailureAtConnectorA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment power failure at connector A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7000 }

equipmentPowerFailureAtConnectorB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment power failure at connector B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7005 }

equipmentPowerFailureAtReturnConnectorA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment power failure at return connector A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7010 }

equipmentPowerFailureAtReturnConnectorB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Equipment power failure at return connector B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7015 }

bridgeAndRollHasOccurred
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Bridge and Roll Has Occurred"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7055 }

bridgeAndRollIsPendingAValidSignal
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Bridge and Roll is Pending a Valid Signal"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7060 }

clockBusFailureShelfControllerA
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Clock Bus Failure - Shelf Controller A"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7160 }

clockBusFailureShelfControllerB
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Clock Bus Failure - Shelf Controller B"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7165 }

ospfHelloFail
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OSPF Hello Fail"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7185 }

openIOSlots
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Open IO Slots"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7200 }

lossOfClockFromMateShelfController
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Clock from Mate Shelf Controller"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 7210 }

odukAlarmIndicationSignalTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Alarm Indication Signal TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13100 }

odukAlarmIndicationSignalTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Alarm Indication Signal TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13105 }

odukLockedDefectTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Locked Defect - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13110 }

odukLockedDefectTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Locked Defect - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13115 }

otukLossOfFrame
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "OTUk: Loss Of Frame"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13120 }

odukOpenConnectionIndicationTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Open Connection Indication TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13125 }

odukOpenConnectionIndicationTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Open Connection Indication TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13130 }

odukTrailTraceIdentifierMismatchTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Trail Trace Identifier Mismatch TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13135 }

odukTrailTraceIdentifierMismatchTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Trail Trace Identifier Mismatch TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13140 }

odukSignalFailureTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Signal Failure - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13145 }

odukSignalFailureTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Signal Failure - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13150 }

odukSignalDegradeTCM1
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Signal Degrade - TCM1"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13155 }

odukSignalDegradeTCM2
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "ODUk Signal Degrade - TCM2"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13160 }

lossOfChannel
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss of Channel"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13165 }

fecMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "FEC Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13170 }

timSectionMonitorTraceIdentifierMismatchFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "TIM Section Monitor - Trace Identifier Mismatch Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13175 }

automaticLaserShutdown
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Laser Shutdown"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13180 }

shutterInsertionLossVariationDegradeLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Shutter Insertion Loss Variation Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13200 }

opticalChannelDeactivationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Channel de-activation failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13205 }

shutterInsertionLossVariationDegradeHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Shutter Insertion Loss Variation Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13210 }

networkTopologyIncomplete
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Network Topology Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13215 }

pluginModuleCommunicationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Plug-in Module Communication Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13220 }

opticalNetworkTypeMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Network Type Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13225 }

laserPowerDegradeLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Laser Power Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13230 }

automaticPowerControlFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Power Control Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13235 }

opticalPowerDegradeHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Power Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13240 }

automaticPowerControlDisabled
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Automatic Power Control Disabled"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13245 }

opticalPowerFailureLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Power Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13250 }

ringIdMismatch
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Ring Id Mismatch"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13255 }

opticalPowerFailureHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Power Failure High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13260 }

lossOfContinuity
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Loss Of Continuity"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13270 }

variableOpticalAttenuatorDegradeLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Variable Optical Attenuator Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13280 }

variableOpticalAttenuatorDegradeHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Variable Optical Attenuator Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13290 }

variableOpticalAttenuatorFailureLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Variable Optical Attenuator Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13300 }

variableOpticalAttenuatorFailureHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Variable Optical Attenuator Failure High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13310 }

laserBiasDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Laser Bias Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13320 }

laserBiasFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "aser Bias Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13330 }

laserTemperatureDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Laser Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13340 }

opticalAmplifierGainDegradeLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Amplifier Gain Degrade Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13350 }

opticalAmplifierGainDegradeHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Amplifier Gain Degrade High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13360 }

opticalAmplifierGainFailureLow
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Amplifier Gain Failure Low"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13370 }

opticalAmplifierGainFailureHigh
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Amplifier Gain Failure High"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13380 }

opticalChannelConnectionFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Channel connection failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13390 }

opticalChannelIncomplete
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Channel Incomplete"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13395 }

opticalChannelActivationFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Channel activation failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13400 }

laserAutoPowerReduction
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Laser Auto Power Reduction"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13410 }

caseTemperatureDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Case Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13420 }

fiberTemperatureDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Fiber Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13430 }

shutterFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Shutter Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13440 }

awgTemperatureDegrade
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "AWG Temperature Degrade"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13450 }

awgTemperatureFailure
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "AWG Temperature Failure"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13460 }

awgOverTemperature
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "AWG Over-Temperature"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13470 }

opticalAmplifierInitialization
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Optical Amplifier Initialization"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13480 }

awgWarmUp
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "AWG Warm Up"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13490 }

incomingSignalLossOnFibreChannelInterface
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Incoming Signal Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13510 }

incomingSynchronizationLossOnFibreChannelInterface
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Incoming Synchronization Loss on Fibre Channel Interface"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13515 }

outOfFrameDetectedByGFPReceiver
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Out Of Frame Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13520 }

clientSignalLossFramesDetectedByGFPReceiver
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Client Signal Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13525 }

clientSychronizationLossFramesDetectedByGFPReceiver
  NOTIFICATION-TYPE
    OBJECTS {
      cerent454NodeTime,
      cerent454AlarmState,
      cerent454AlarmObjectType,
      cerent454AlarmObjectIndex,
      cerent454AlarmSlotNumber,
      cerent454AlarmPortNumber,
      cerent454AlarmLineNumber,
      cerent454AlarmObjectName
    }
    STATUS current
    DESCRIPTION "Client Sychronization Loss Frames Detected by GFP Receiver"
    --#SUMMARY "%d Object:%d Index:%d Slot:%d Port:%d AID:%s"
    --#ARGUMENTS {$2, $3, $4, $5, $6, $8}
    --#GENERIC 6
    --#SOURCE_ID "A"
    --#TIMEINDEX 0
    ::= { cerent454V2Events 13530 }

node454Group OBJECT-GROUP
        OBJECTS {
          cerent454SoftwareVersion }
        STATUS current
        DESCRIPTION
          "The group for node related objects"
        ::= { cerent454Groups 10 }

alarm454Group OBJECT-GROUP
        OBJECTS {
          cerent454AlarmCount,
          cerent454AlarmObjectIndex,
          cerent454AlarmObjectType,
          cerent454AlarmSlotNumber,
          cerent454AlarmPortNumber,
          cerent454AlarmLineNumber,
          cerent454AlarmType,
          cerent454AlarmState,
          cerent454AlarmTimeStamp,
          cerent454AlarmObjectName,
          cerent454AlarmAdditionalInfo
        }
        STATUS current
        DESCRIPTION
          "The group for node related objects"
        ::= { cerent454Groups 20 }

event454Group NOTIFICATION-GROUP
     NOTIFICATIONS {
       alarmUnknown,
       alarmCutoffIsInManualMode,
       failureDetectedExternalToTheNE,
       externalError,
       excessiveSwitching,
       sdccTerminationFailure,
       incomingFailureCondition,
       alarmIndicationSignal,
       alarmIndicationSignalLine,
       alarmIndicationSignalPath,
       alarmIndicationSignalVT,
       channelFailureAPS,
       channelByteFailureAPS,
       channelProtectionSwitchingChannelMatchFailureAPS,
       channelAutomaticProtectionSwitchModeMismatchAPS,
       channelFarEndProtectionLineFailureAPS,
       inconsistentAPSCode,
       improperAPSCode,
       nodeIdMismatch,
       channelDefaultKAPS,
       connectionLoss,
       bipolarViolation,
       carrierLossOnTheLAN,
       concatenationErrorSTS,
       excessCollisionsOnTheLAN,
       facilityCriticalAlarmCausedByDS3FacilityFailure,
       farEndAIS,
       farEndMultipleDS1LOSDetectedOnDS3,
       farEndDS1EqptFailNonServiceAffecting,
       farEndDS1EqptFailServiceAffecting,
       farEndSingleDS1LOS,
       farEndDS3EqptFailNonServiceAffecting,
       farEndDS3EqptFailServiceAffecting,
       farEndCommonEquipmentFailureNonServiceAffecting,
       farEndIDLE,
       farEndLOS,
       farEndLOF,
       farEndBlockError,
       ds3IdleCondition,
       lossOfFrame,
       lossOfPointer,
       lossOfPointerPath,
       lossOfPointerVT,
       lossOfSignal,
       outOfFrame,
       pathSelectorInabilityToSwitchToAValidSignal,
       remoteAlarmIndication,
       remoteFailureIndication,
       remoteFailureIndicationLine,
       remoteFailureIndicationPath,
       remoteFailureIndicationVT,
       signalDegrade,
       severelyErroredFrame,
       signalFailure,
       signalLabelMismatchFailure,
       payloadDefectIndication,
       payloadDefectIndicationPath,
       payloadLabelMismatchPath,
       signalLabelMismatchFailurePayloadLabelMismatchVT,
       unequippedPath,
       signalLabelMismatchFailureUnequippedVT,
       lossOfSynchronization,
       outOfSynchronization,
       primarySynchronizationReferenceFailure,
       secondarySynchronizationReferenceFailure,
       thirdSynchronizationReferenceFailure,
       fourthSynchronizationReferenceFailure,
       fifthSynchronizationReferenceFailure,
       sixthSynchronizationReferenceFailure,
       failedToReceiveSynchronizationStatusMessage,
       synchronizationStatusMessagesAreDisabledOnThisInterface,
       primaryReferenceSourceStratum1Traceable,
       synchronizedTraceabilityUnknown,
       stratum2Traceable,
       transitNodeClockTraceable,
       stratum3ETraceable,
       stratum3Traceable,
       sonetMinimumClockTraceable,
       stratum4Traceable,
       doNotUseForSynchronization,
       reservedForNetworkSynchronizationUse,
       outgoingFailureCondition,
       remoteDefectIndicationLine,
       remoteDefectIndicationPath,
       freeRunningSynchronizationMode,
       holdoverSynchronizationMode,
       fastStartSynchronizationMode,
       internalHardwareFaultOrFailure,
       errorInternalToTheNEDetected,
       internalMessageError,
       mismatchOfEquipmentAndAttributes,
       watchdogTimerTimeout,
       softwareFaultOrFailure,
       softwareFaultDataIntegrityFault,
       programFailure,
       controlEquipmentFailure,
       controlEquipmentPrimaryNonVolatileBackupMemoryFailure,
       cntrlEqptSecondaryNonVolatileBackupMemoryFailed,
       controlEquipmentControlBusFailure,
       controlEquipmentControlBus1Failure,
       controlEquipmentControlBus2Failure,
       communicationFailureTCCAToShelfSLOT1,
       communicationFailureTCCAToShelfSLOT2,
       communicationFailureTCCAToShelfSLOT3,
       communicationFailureTCCAToShelfSLOT4,
       communicationFailureTCCAToShelfSLOT5,
       communicationFailureTCCAToShelfSLOT6,
       communicationFailureTCCAToShelfSLOT7,
       communicationFailureTCCAToShelfSLOT8,
       communicationFailureTCCAToShelfSLOT9,
       communicationFailureTCCAToShelfSLOT10,
       communicationFailureTCCAToShelfSLOT11,
       communicationFailureTCCAToShelfSLOT12,
       communicationFailureTCCAToShelfSLOT13,
       communicationFailureTCCAToShelfSLOT14,
       communicationFailureTCCAToShelfSLOT15,
       communicationFailureTCCAToShelfSLOT16,
       communicationFailureTCCAToShelfSLOT17,
       tccAToDCCAProcessorCommunicationFailure,
       communicationFailureTCCBToShelfSLOT1,
       communicationFailureTCCBToShelfSLOT2,
       communicationFailureTCCBToShelfSLOT3,
       communicationFailureTCCBToShelfSLOT4,
       communicationFailureTCCBToShelfSLOT5,
       communicationFailureTCCBToShelfSLOT6,
       communicationFailureTCCBToShelfSLOT7,
       communicationFailureTCCBToShelfSLOT8,
       communicationFailureTCCBToShelfSLOT9,
       communicationFailureTCCBToShelfSLOT10,
       communicationFailureTCCBToShelfSLOT11,
       communicationFailureTCCBToShelfSLOT12,
       communicationFailureTCCBToShelfSLOT13,
       communicationFailureTCCBToShelfSLOT14,
       communicationFailureTCCBToShelfSLOT15,
       communicationFailureTCCBToShelfSLOT16,
       communicationFailureTCCBToShelfSLOT17,
       communicationFailureTCCPBToTCCJBprocessor,
       controlEquipmentControlCommunicationsEquipmentFailure,
       controlEquipmentControlProcessorFailure,
       controlEquipmentWorkingMemoryFailure,
       interconnectionEquipmentFailure,
       interconnectionEquipmentFailurePayloadBus1Working,
       interconnectionEquipmentFailurePayloadBus2Working,
       interconnectionEquipmentFailurePayloadBus3Working,
       interconnectionEquipmentFailurePayloadBus4Working,
       interconnectionEquipmentFailurePayloadBus5Working,
       interconnectionEquipmentFailurePayloadBus6Working,
       interconnectionEquipmentFailurePayloadBus7Working,
       interconnectionEquipmentFailurePayloadBus8Working,
       interconnectionEquipmentFailurePayloadBus9Working,
       interconnectionEquipmentFailurePayloadBus10Working,
       interconnectionEquipmentFailurePayloadBus11Working,
       interconnectionEquipmentFailurePayloadBus12Working,
       interconnectionEquipmentFailurePayloadBus1Protect,
       interconnectionEquipmentFailurePayloadBus2Protect,
       interconnectionEquipmentFailurePayloadBus3Protect,
       interconnectionEquipmentFailurePayloadBus4Protect,
       interconnectionEquipmentFailurePayloadBus5Protect,
       interconnectionEquipmentFailurePayloadBus6Protect,
       interconnectionEquipmentFailurePayloadBus7Protect,
       interconnectionEquipmentFailurePayloadBus8Protect,
       interconnectionEquipmentFailurePayloadBus9Protect,
       interconnectionEquipmentFailurePayloadBus10Protect,
       interconnectionEquipmentFailurePayloadBus11Protect,
       interconnectionEquipmentFailurePayloadBus12Protect,
       interconnectionEqptTimeSlotInterchangeEqptFailure,
       equipmentFailure,
       highTemperature,
       equipmentFailureInvalidMACAddress,
       equipmentFailureBoardFailure,
       diagnosticFailure,
       equipmentFailureMediumAccessControl,
       facilityTerminationEquipmentFailure,
       automaticLaserShutoffDueToHighTemperature,
       failureToReleaseFromProtection,
       facilityTerminationEquipmentReceiverFailure,
       facilityTerminationEquipmentTransmitFailure,
       facilityTerminationEquipmentReceiverMissing,
       facilityTerminationEquipmentTransmitterMissing,
       failureToSwitchToProtection,
       failureToSwitchToProtectionRing,
       failureToSwitchToProtectionSpan,
       failureToSwitchToProtectionPath,
       failureOfCoolingFanTray,
       equipmentUnitPlugIn,
       nePowerFailureAtConnector,
       powerFailureFuseAlarm,
       synchronizationUnitFailure,
       synchronizationSwitchingEquipmentFailure,
       equipmentUnitUnplug,
       loopback,
       loopbackDueToFEACCommandDS1,
       loopbackCommandSentToFarEndDS1,
       ds3LoopbackDueToFEACCommand,
       loopbackCommandSentToFarEndDS3,
       loopbackDueToFarEndCommandDS2,
       loopbackCommandSentToFarEndDS2,
       loopbackFacility,
       loopbackNetwork,
       loopbackTerminal,
       manuallyCausedAbnormalCondition,
       newRootDiscoveredInBridgedNetwork,
       topologyChangeDiscoveredInBridgedNetwork,
       normalCondition,
       embeddedOperationsChannelFailureLinkDown,
       peerStateMismatch,
       proceduralError,
       improperRemoval,
       duplicateNodeID,
       blsrOutOfSync,
       resynchronizedBLSRTables,
       protectionUnitNotAvailable,
       performanceMonitorThresholdCrossingAlert,
       occurrenceOfAProtectionSwitchingEvent,
       recoveryOrServiceProtectionActionHasBeenInitiated,
       automaticSystemReset,
       automaticUPSRSwitchCausedByAIS,
       automaticUPSRSwitchCausedByLOP,
       automaticUPSRSwitchCausedByUneq,
       automaticUPSRSwitchCausedByPDI,
       automaticUPSRSwitchCausedBySfber,
       automaticUPSRSwitchCausedBySdber,
       coldRestart,
       workingFacilityOrEqptForcedSwitchedToWorking,
       workingFacilityOrEqptForcedSwitchedToWorkingRing,
       workingFacilityOrEqptForcedSwitchedToWorkingSpan,
       workingFacilityOrEqptForcedSwitchedProtectionUnit,
       workingFacilityOrEqptForcedSwitchedProtectionUnitRing,
       workingFacilityOrEqptForcedSwitchedProtectionUnitSpan,
       workingFacilityOrEqptForcedSwitchedProtectionUnitPath,
       initializationInitiated,
       lockoutOfProtection,
       lockoutOfProtectionRing,
       lockoutOfProtectionSpan,
       lockoutOfProtectionPath,
       lockoutOfWorking,
       lockoutOfWorkingRing,
       lockoutOfWorkingSpan,
       manualSystemReset,
       manualSwitchToInternalClock,
       manualSwitchToPrimaryReference,
       manualSwitchToSecondReference,
       manualSwitchToThirdReference,
       manualSwitchToFourthReference,
       manualSwitchToFifthReference,
       manualSwitchToSixthReference,
       manualSwitchOfWorkingFacilityOrEqptToProtectionRing,
       manualSwitchOfWorkingFacilityOrEqptToProtectionSpan,
       manualSwitchOfWorkingFacilityOrEqptToProtection,
       manualSwitchOfWorkingFacilityOrEqptToProtectionUnit,
       workingFacilityOrEqptManualSwitchToProtectionUnitRing,
       workingFacilityOrEqptManualSwitchToProtectionUnitSpan,
       manualSwitchOfWorkingFacilityOrEqptToProtectionPath,
       powerFailureRestart,
       ringIsSquelchingTraffic,
       softwareDownloadInProgress,
       switchToInternalClock,
       switchToPrimaryReference,
       switchToSecondReference,
       switchToThirdReference,
       switchToFourthReference,
       switchToFifthReference,
       switchToSixthReference,
       systemReboot,
       switchedBackToWorking,
       switchedToProtection,
       warmRestart,
       ringIsInWaitToRestoreState,
       manualSwitchRequest,
       forcedSwitchRequest,
       lockoutSwitchRequest,
       rmonHistoriesAndAlarmsReset,
       rmonThresholdCrossingAlarm,
       alarmsSuppressedByUserCommand,
       alarmsSuppressedForMaintenance,
       switchingMatrixModuleFailure,
       lanConnectionPolarityReversed,
       autonomousPerformanceMonitoringReportMessageInhibited,
       ioSlotToXCONCommunicationFailure,
       stsPathTraceIdentifierMismatch,
       nodePowerFailureAtConnectorA,
       nodePowerFailureAtConnectorB,
       freeMemoryOnCardVeryLow,
       freeMemoryOnCardNearZero,
       exerciseRing,
       exerciseSpan,
       squelchingPath,
       extraTrafficPreempted,
       farEndLockoutOfWorkingRing,
       farEndLockoutOfWorkingSpan,
       farEndLockoutOfProtectionRing,
       farEndLockoutOfProtectionAllSpans,
       farEndWorkingFacilityForcedToSwitchToProtectionUnitRing,
       farEndWorkingFacilityForcedToSwitchToProtectionUnitSpan,
       farEndManualSwitchOfWorkingFacilityToProtectionUnitRing,
       farEndManualSwitchOfWorkingFacilityToProtectionUnitSpan,
       farEndExerciseRing,
       farEndExerciseSpan,
       farEndBERThresholdPassedForSignalFailureRing,
       farEndBERThresholdPassedForSignalFailureSpan,
       farEndBERThresholdPassedForSignalDegradeRing,
       farEndBERThresholdPassedForSignalDegradeSpan,
       channelFarEndProtectionLineSignalDegradeAPS,
       ringSwitchIsActiveOnTheEastSide,
       ringSwitchIsActiveOnTheWestSide,
       spanSwitchIsActiveOnTheEastSide,
       spanSwitchIsActiveOnTheWestSide,
       uniDirectionalFullPassThroughIsActive,
       biDirectionalFullPassThroughIsActive,
       kBytePassThroughIsActive,
       ringIsSegmented,
       ringTopologyIsUnderConstruction,
       lockoutOfProtectionAllSpans,
       farEndOfFiberIsProvisionedWithDifferentRingID,
       bothEndsOfFiberProvisionedAsEastOrBothAsWest,
       securityInvalidLoginUsernameSeeAuditTrail,
       autonomousMessagesInhibited,
       trafficStormLANtemporarilyDisabled,
       tl1ReptDbchgMessagesInhibited,
       userIdHasExpired,
       partialFanFailure,
       forceSwitchRequestOnRing,
       forceSwitchRequestOnSpan,
       lockoutSwitchRequestOnRing,
       lockoutSwitchRequestOnSpan,
       manualSwitchRequestOnRing,
       manualSwitchRequestOnSpan,
       communicationFailurePeerToPeerSlotControlBusA,
       communicationFailurePeerToPeerSlotControlBusB,
       controllerAToShelfSlotCommunicationFailure,
       controllerBToShelfSlotCommunicationFailure,
       interconnectionEquipmentFailureWorkingPayloadBus,
       interconnectionEquipmentFailureProtectPayloadBus,
       inhibitSwitchToProtectRequestOnEquipment,
       inhibitSwitchToWorkingRequestOnEquipment,
       exerciseRingCompleted,
       exerciseSpanCompleted,
       spanIsInWaitToRestoreState,
       exerciseRingFailed,
       exerciseSpanFailed,
       farEndLockoutOfProtectionChannelInSpan,
       manufacturingEepromFailure,
       replaceableEquipmentIsMissing,
       softwareDownloadFailed,
       extraTrafficDropped,
       pktLossDueToOversubscribedXmit,
       pktLossDueToOversubscribedRcv,
       excessiveEthernetFlowCtlXmited,
       excessiveEthernetFlowCtlRecvd,
       transportLayerFailure,
       etherHdgeInternalFifoUnderrun,
       synchronizationReferenceFrequencyOutOfBounds,
       ntpOrSntpHostFailure,
       peerCardNotResponding,
       alarmsAndEventsSuppressedForThisObject,
       ds3FrameFormatMismatch,
       timSectionTraceIdentifierMismatchFailure,
       sdhMultiplexSectionAlarmIndicationSignal,
       sdhMultiplexSectionRemoteFailureIndication,
       sdhHighOrderTraceIdentifierMismatch,
       sdhAdministrationUnitAlarmIndicationSignal,
       sdhAdministrationUnitLossofPointer,
       sdhSLMFHighOrderUnequippedPath,
       sdhSLMFHighOrderPathLabelMismatch,
       sdhHighOrderRemoteFailureIndication,
       sdhTributaryUnitLossofPointer,
       sdhTributaryUnitAlarmIndicationSignal,
       sdhSLMFLowOrderUnequippedPath,
       sdhSLMFLowOrderPathLabelMismatch,
       sdhLowOrderTraceIdentifierMismatch,
       sdhLowOrderRemoteFailureIndication,
       g811PrimaryReferenceClockTraceable,
       g812TransitNodeClockTraceable,
       g812LocalNodeClockTraceable,
       g813SynchronousEqptTimingSourceTraceable,
       loopbackDueToFEACCommandE1,
       loopbackCommandSentToFarEndE1,
       loopbackDueToFEACCommandE3,
       farEndMultipleE1LOSDetectedOnE3,
       farEndE1EqptFailNonServiceAffecting,
       farEndE1EqptFailServiceAffecting,
       farEndSingleE1LOS,
       farEndE3EqptFailServiceAffecting,
       loopbackCommandSentToFarEndE3,
       farEndE3EqptFailNonServiceAffecting,
       lowVoltBatteryA,
       highVoltBatteryA,
       lowVoltBatteryB,
       highVoltBatteryB,
       msspRingOutOfSync,
       resynchronizedMSSPTables,
       automaticSNCPSwitchCausedByAIS,
       automaticSNCPSwitchCausedByLOP,
       automaticSNCPSwitchCausedByUneq,
       automaticSNCPSwitchCausedByPDI,
       automaticSNCPSwitchCausedBySfber,
       automaticSNCPSwitchCausedBySdber,
       concatenationErrorSTM,
       idleConditionE3,
       channelMSSPInconsistentAPSCode,
       channelMSSPImproperAPSCodeAPS,
       channelMSSPNodeIdMismatchAPS,
       channelMSSPDefaultKAPS,
       channelMSSPConnectionLossAPS,
       minimumClockTraceableSDH,
       lineIsInWaitToRestoreStateSDH,
       passedBERThresholdForSignalDegradeHighOrder,
       passedBERThresholdForSignalFailHighOrder,
       passedBERThresholdForSignalDegradeLowOrder,
       passedBERThresholdForSignalFailLowOrder,
       failureToSwitchToProtectionHighOrder,
       failureToSwitchToProtectionLowOrder,
       a8b10bOutOfSync,
       odukAlarmIndicationSignal,
       otukAlarmIndicationSignal,
       otukSMBackwardDefectIndication,
       odukBackwardDefectIndication,
       fecUncorrectedWord,
       gccTerminationFailure,
       otukIncomingAlignmentError,
       odukLockedDefectPm,
       lossOfMultiFrame,
       odukOpenConnectionIndication,
       payloadTypeIdentifierMismatch,
       odukTrailTraceIdentifierMismatch,
       otukTrailTraceIdentifierMismatch,
       equipmentHighLaserBias,
       equipmentHighLaserTemp,
       equipmentHighLaserPeltier,
       equipmentHighRxPower,
       equipmentHighTxPower,
       equipmentHighTransceiverVoltage,
       equipmentLowLaserBias,
       equipmentLowLaserTemp,
       equipmentLowLaserPeltier,
       equipmentLowRxPower,
       equipmentLowTxPower,
       equipmentLowTransceiverVoltage,
       equipmentRxLocked,
       equipmentSquelched,
       equipmentTxLocked,
       otukSignalFailure,
       odukSignalFailure,
       otukSignalDegrade,
       odukSignalDegrade,
       pluggablePortMissing,
       pluggablePortRateMismatch,
       pluggablePortSecurityCodeMismatch,
       tciNotSelected,
       tci1ClockFailure,
       odukPMBackwardDefectIndication,
       odukTCM1BackwardDefectIndication,
       odukTCM2BackwardDefectIndication,
       equipmentHighRxTemperature,
       equipmentLowRxTemperature,
       tci2ClockFailure,
       equipmentWavelengthMismatch,
       dspCommunicationFailure,
       dspFailure,
       laserApproachingEndOfLife,
       crossconnectLoopback,
       adminLogoutOfUser,
       userLockedOut,
       adminLockoutOfUser,
       adminLockoutClear,
       invalidLoginUsername,
       invalidLoginPassword,
       invalidLoginLockedOut,
       invalidLoginAlreadyLoggedOn,
       loginOfUser,
       automaticLogoutOfIdleUser,
       logoutOfUser,
       firewallHasBeenDisabled,
       connectionEquipmentMismatch,
       disableInactiveUser,
       disableInactiveClear,
       batteryFailure,
       extremeHighVolt,
       extremeLowVolt,
       highVolt,
       lowVolt,
       suspendUser,
       suspendUserClear,
       lineDCCTerminationFailure,
       multiplexSectionDCCTerminationFailure,
       gigabitEthernetOutOfSync,
       sequenceMismatch,
       lossOfAlignment,
       outOfUseAdministrativeCommand,
       outOfUseTransportFailure,
       vcatGroupDown,
       vcatGroupDegraded,
       vcatGroupIncomplete,
       alarmIndicationSignalInTX,
       remoteAlarmIndicationInTX,
       kbyteChannelFailure,
       apsInvalidMode,
       ipAddressAlreadyInUseWithinTheSameDCCArea,
       nodeNameAlreadyInUseWithinTheSameDCCArea,
       rearPanelEthernetLinkRemoved,
       manualSwitchToProtectResultedInNoTrafficSwitch,
       manualSwitchBackToWorkingResultedInNoTrafficSwitch,
       forcedSwitchToProtectionResultedInNoTrafficSwitch,
       forcedSwitchBackToWorkingResultedInNoTrafficSwitch,
       duplicateSerialNumberDetectedOnAPluggableEntity,
       lossOfSignalForOpticalChannel,
       encapsulationMismatchPath,
       encapsulationMismatchVT,
       encapsulationMismatchHighOrderPath,
       encapsulationMismatchLowOrderPath,
       gfpUserPayloadMismatch,
       gfpFibreChannelDistanceExtensionMismatch,
       gfpFibreChannelDistanceExtensionBufferStarvation,
       fibreChannelDistanceExtensionCreditStarvation,
       gfpClientSignalFailDetected,
       gfpLossOfFrameDelineation,
       gfpExtensionHeaderMismatch,
       lcasVCGMemberTxSideInADDState,
       lcasVCGMemberTxSideInDNUState,
       lcasControlWordCRCCheckFailure,
       lcasVCGMemberRxSideInFAILState,
       signalLossOnDataInterface,
       synchronizationLossOnDataInterface,
       portFAIL,
       unreachablePortTargetPower,
       portAddPowerDegradeLow,
       portAddPowerDegradeHigh,
       portAddPowerFailLow,
       portAddPowerFailHigh,
       automaticWDMANSFinished,
       lossOfSignalForOverhead,
       opticalSafetyRemoteInterlockOn,
       automaticPowerControlCorrectionSkipped,
       apcCannotSetValueDueToRangeLimits,
       farEndManualSwitchBackToWorkingSpan,
       farEndForcedSwitchBackToWorkingSpan,
       universalTransponderModuleHardwareFailure,
       universalTransponderModuleCommunicationFailure,
       pluginModuleRangeSettingsMismatch,
       automaticPowerControlTerminatedOnManualRequest,
       oduk1AlarmIndicationSignal,
       oduk2AlarmIndicationSignal,
       oduk3AlarmIndicationSignal,
       oduk4AlarmIndicationSignal,
       temperatureReadingMismatchBetweenSCCards,
       voltageReadingMismatchBetweenSCCards,
       alarmsSuppressedOnOutOfGroupVCATMember,
       blsrSoftwareVersionMismatch,
       optimized1Plus1APSPrimaryFacility,
       optimized1Plus1APSPrimarySectionMismatch,
       optimized1Plus1APSInvalidPrimarySection,
       compositeClockHighLineVoltage,
       berThresholdExceededForSignalDegradeVT,
       berThresholdExceededForSignalFailureVT,
       spanLengthOutOfRange,
       vtPathTraceIdentifierMismatch,
       lossOfFrameInTX,
       provisioningMismatch,
       sectionTraceIdentifierMismatch,
       regeneratorSectionTraceIdentifierMismatch,
       switchingMatrixModuleFailureWorking,
       switchingMatrixModuleFailureProtect,
       slotCommunicationDisabled,
       sessionTimeLimitExpired,
       userPasswordChangeRequired,
       isisAdjacencyFailure,
       msspSoftwareVersionMismatch,
       remoteAuthenticationFailSeeAuditLog,
       ringIsSquelchingSTSTraffic,
       ringIsSquelchingVTTraffic,
       archivalOfAuditLogFailed,
       rprWrapped,
       shelfCommunicationFailure,
       duplicatedShelfIdentifier,
       softwareMismatch,
       lmpFailure,
       opticalTerminationIncomplete,
       forwardDefectIndication,
       payloadMissingIndication,
       spanLossNotChecked,
       ringIsSquelchingHigherOrderTraffic,
       ringIsSquelchingLowerOrderTraffic,
       badPacketCountExceedsThreshold,
       linkLayerKeepAliveFailure,
       autonegotiationRemoteFailureIndication,
       trailSignalFail,
       ds1LoopbackCommandSentToFarEnd,
       multiplexSectionSignalDegraded,
       multiplexSectionExcessiveErrors,
       highOrderPathSignalDegraded,
       highOrderPathExcessiveErrors,
       lowOrderPathSignalDegraded,
       lowOrderPathExcessiveErrors,
       regeneratorSectionDCCTerminationFailure,
       networkMemoryPoolLow,
       ospfRoutingTableOverflow,
       autoLaserShutdownDisabled,
       rprProtectionIsActive,
       maxRPRStationNumberExceeded,
       rprProtectionConfigurationMismatched,
       reservedBandwidthLinkRateExceededOnRinglet0,
       reservedBandwidthLinkRateExceededOnRinglet1,
       rprInterfaceInPassThroughMode,
       rprPeerNodeIsMissing,
       rprRIFailure,
       rprSignalFailure,
       rprSignalDegrade,
       rprSpanMismatch,
       workQueueFull,
       equipmentPowerFailureAtConnectorA,
       equipmentPowerFailureAtConnectorB,
       equipmentPowerFailureAtReturnConnectorA,
       equipmentPowerFailureAtReturnConnectorB,
       ospfHelloFail,
       openIOSlots,
       lossOfClockFromMateShelfController,
       enhancedRemoteFailureIndicationPathServer,
       enhancedRemoteFailureIndicationPathConnectivity,
       enhancedRemoteFailureIndicationPathPayload,
       securityIntrusionAttemptDetectedSeeAuditLog,
       securityIntrusionIncorrectUsername,
       odukAlarmIndicationSignalTCM1,
       odukAlarmIndicationSignalTCM2,
       odukLockedDefectTCM1,
       odukLockedDefectTCM2,
       otukLossOfFrame,
       odukOpenConnectionIndicationTCM1,
       odukOpenConnectionIndicationTCM2,
       odukTrailTraceIdentifierMismatchTCM1,
       odukTrailTraceIdentifierMismatchTCM2,
       odukSignalFailureTCM1,
       odukSignalFailureTCM2,
       odukSignalDegradeTCM1,
       odukSignalDegradeTCM2,
       lossOfChannel,
       fecMismatch,
       timSectionMonitorTraceIdentifierMismatchFailure,
       automaticLaserShutdown,
       shutterInsertionLossVariationDegradeLow,
       opticalChannelDeactivationFailure,
       shutterInsertionLossVariationDegradeHigh,
       networkTopologyIncomplete,
       pluginModuleCommunicationFailure,
       opticalNetworkTypeMismatch,
       forcedSwitchToPrimaryReference,
       forcedSwitchToSecondReference,
       forcedSwitchToThirdReference,
       forcedSwitchToInternalClock,
       industrialHighTemperature,
       laserPowerDegradeLow,
       automaticPowerControlFailure,
       opticalPowerDegradeHigh,
       automaticPowerControlDisabled,
       opticalPowerFailureLow,
       ringIdMismatch,
       opticalPowerFailureHigh,
       lossOfContinuity,
       variableOpticalAttenuatorDegradeLow,
       variableOpticalAttenuatorDegradeHigh,
       variableOpticalAttenuatorFailureLow,
       variableOpticalAttenuatorFailureHigh,
       laserBiasDegrade,
       laserBiasFailure,
       laserTemperatureDegrade,
       opticalAmplifierGainDegradeLow,
       opticalAmplifierGainDegradeHigh,
       opticalAmplifierGainFailureLow,
       opticalAmplifierGainFailureHigh,
       opticalChannelConnectionFailure,
       opticalChannelIncomplete,
       opticalChannelActivationFailure,
       laserAutoPowerReduction,
       caseTemperatureDegrade,
       fiberTemperatureDegrade,
       shutterFailure,
       awgTemperatureDegrade,
       awgTemperatureFailure,
       awgOverTemperature,
       opticalAmplifierInitialization,
       awgWarmUp,
       incomingSignalLossOnFibreChannelInterface,
       incomingSynchronizationLossOnFibreChannelInterface,
       outOfFrameDetectedByGFPReceiver,
       clientSignalLossFramesDetectedByGFPReceiver,
       clientSychronizationLossFramesDetectedByGFPReceiver,
       bridgeAndRollHasOccurred,
       bridgeAndRollIsPendingAValidSignal, 
       clockBusFailureShelfControllerA,
       clockBusFailureShelfControllerB,
       waitToRestore,
       extremeHighVoltBatteryA,
       extremeLowVoltBatteryA,
       extremeHighVoltBatteryB,
       extremeLowVoltBatteryB,
       iosConfigCopyFailed,
       iosConfigCopyInProgress,
       signalingUnableToSetupCircuit,
       errorInStartupConfig,
       noStartupConfig,
       needToSaveRunningConfig,
       invalidAlarm,
       rsvpHelloFsmToNeighborDown,
       securityInvalidLoginUsernameSeeAuditLog,
       databaseBackupFailed,
       databaseRestoreFailed,
       lMPHelloFsmToControlChannelDown,
       lMPNeighborDiscoveryHasFailed,
       auditLog80PercentFull,
       moduleCommunicationFailure,
       auditLog100PercentFullOldestRecordsWillBeLost,
       standbyDatabaseOutOfSync,
       redundantPowerCapabilityLost,
       sdhAdministrationUnitLossOfMultiframe,
       sdhSpanIsInWaitToRestoreState,
       berThresholdExceededForSignalDegradeLine,
       berThresholdExceededForSignalDegradePath,
       berThresholdExceededForSignalFailureLine,
       berThresholdExceededForSignalFailurePath,
       unauthorizedIncomingSignalingRequest
     }
        STATUS current
        DESCRIPTION
          "The notifications for Cisco ONS 15454"
        ::= { cerent454Groups 30 }

-- This definition of group will move to a cerentCommon modules
-- eventually.

cerent454CommonGroup OBJECT-GROUP
        OBJECTS {
--          cerentNotificationCategory,
          cerent454EnableNotification,
          cerent454NodeTime,
          cerent454SentNotifications,
          cerent454LastChangeTime
          }
        STATUS current
        DESCRIPTION
          "The objects for storing all the current alarms"
        ::= { cerent454Groups 40 }

-- This group covers for threshold display and TCA trap

cerentThresholdGroup OBJECT-GROUP
        OBJECTS {
          cerent454ThresholdMonitorType,
          cerent454ThresholdLocation,
          cerent454ThresholdPeriod,
          cerent454ThresholdSetValue,
          cerent454ThresholdCurrentValue,
          cerent454ThresholdDetectType  
        }
        STATUS current
        DESCRIPTION
          "The objects for storing all the current alarms"
        ::= { cerent454Groups 50 }

-- the compliance specification for agent developers

cerent454BasicCompliance MODULE-COMPLIANCE
       STATUS current
       DESCRIPTION
         "The basic implementation requirements for Cisco ONS 15454 MIB"
       MODULE
         MANDATORY-GROUPS {
           node454Group,
           event454Group
        }
       ::= { cerent454Compliance 10 }

END
