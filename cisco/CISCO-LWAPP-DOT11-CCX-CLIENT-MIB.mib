-- *******************************************************************
-- CISCO-LWAPP-DOT11-CCXV5-CLIENT-MIB.my
-- July 2006, Ambika Mohanty
--
-- Copyright (c) 2006 by Cisco Systems, Inc.
-- All rights reserved.
-- *******************************************************************

CISCO-LWAPP-DOT11-CCX-CLIENT-MIB DEFINITIONS ::= BEGIN

IMPORTS
        MODULE-IDENTITY,
        OBJECT-TYPE,
        Unsigned32
                FROM SNMPv2-SMI
        MODULE-COMPLIANCE,
        OBJECT-GROUP
                FROM SNMPv2-CONF
        MacAddress,
        TruthValue,
        RowStatus,
        TimeStamp,
	TEXTUAL-CONVENTION
                FROM SNMPv2-TC
	CiscoMilliSeconds
	        FROM CISCO-TC
        cldcClientMacAddress,
        ciscoLwappDot11ClientCcxMIBObjects
                FROM CISCO-LWAPP-DOT11-CLIENT-MIB
        ciscoMgmt
                FROM CISCO-SMI;

--********************************************************************
--*  MODULE IDENTITY
--********************************************************************

ciscoLwappDot11CcxClientMIB      MODULE-IDENTITY
        LAST-UPDATED   "200606240000Z"
        ORGANIZATION   "Cisco Systems Inc."
        CONTACT-INFO
               "        Cisco Systems,
                        Customer Service
                Postal: 170 West Tasman Drive
                        San Jose, CA  95134
                        USA
                   Tel: +1 800 553-NETS

                 Email: cs-wnbu-snmp@cisco.com"

        DESCRIPTION
                "This MIB is intended to be implemented on all those
                devices operating as Central Controllers (CC) that
                terminate the Light Weight Access Point Protocol
                (LWAPP) tunnel from Light-weight  Access Points.

                Link Test is performed to learn the backhaul link
                quality between two mesh neighboring mesh nodes.

                The arrangement of the controller
                (referred to as CC in the diagram) and mesh nodes
                (RAP and MAP) LWAPP APs ,client(MN) and NMS appear
                as follows.

                 +.......+                 +.......+
                 +       +                 +       +
                 +  NMS  +                 +  NMS  +
                 +       +                 +       +
                 +.......+                 +.......+
                    .                         .
                 .    .                     .   .
              .         .                .        .
            .            .             .            .
        +......+     +......+     +......+           +......+
        +      +     +      +     +      +           +      +
        +  CC  +     +  CC  +     +  CC  +           +  CC  +
        +      +     +      +     +      +           +      +
        +......+     +......+     +......+           +......+
          ..            .             .                 .
          ..            .             .                 .
         .  .            .             .                 .
        .    .            .             .                 .
       .      .            .             .                 .
      .        .            .             .                 .
   +......+ +......+     +......+      +......+          +......+
   +      + +      +     +      +      +      +          +      +
   +  RAP + +  RAP +     +  RAP  +     +  RAP +          +  RAP +
   +      + +      +     +      +      +      +          +      +
   +......+ +......+     +......+      +......+          +......+
      .        .              .             .                 .
       .        .              .             .                 .
        .        .              .             .                 .
        .          .              .             .                 .
        .           .              .             .                 .
      +......+ +......+     +......+      +......+          +......+
      +      + +      +     +      +      +      +          +      +
      +  MAP + +  MN  +     +  MAP +      +  MAP +          +  MAP +
      +      + +      +     +      +      +      +          +      +
      +......+ +......+     +......+      +......+          +......+
          .                    .                          ..    .
          . .                  .                     ..        .
          .   .                .                  ..            .
          .     .              .              .                .
      +......+ +......+     +......+      +......+.         +......+
      +      + +      +     +      +      +      +          +      +
      +  MAP + +  MAP +     +  MAP +      +  MAP +          +  MN  +
      +      + +      +     +      +      +      +          +      +
      +......+ +......+     +......+      +......+          +......+




                The LWAPP tunnel exists between the controller and
                the APs.  The MNs communicate with the APs through
                the protocol defined by the 802.11 standard.  The
                controllers and the IDS systems exchange information
                through Cisco proprietary event exchange mechanisms.

                LWAPP APs, upon bootup, discover and join one of the
                controllers and the controller pushes the
                configuration, that includes the WLAN parameters, to
                the LWAPP APs. The APs then encapsulate all the 802.11
                frames from wireless clients inside LWAPP frames and
                forward the LWAPP frames to the controller.

                                   GLOSSARY

                Access Point ( AP )

                An entity that contains an 802.11 medium access
                control ( MAC ) and physical layer ( PHY ) interface
                and provides access to the distribution services via
                the wireless medium for associated clients.

                LWAPP APs encapsulate all the 802.11 frames in
                LWAPP frames and sends them to the controller to which
                it is logically connected.

                Central Controller ( CC )

                The central entity that terminates the LWAPP protocol
                tunnel from the LWAPP APs.  Throughout this MIB,
                this entity is also referred to as 'controller'.

                Mobile Node ( MN )

                A roaming 802.11 wireless device in a wireless
                network associated with an access point. Mobile Node
                and client are used interchangeably.

                Network Management System ( NMS )

                The station from which the administrator manages the
                wired and wireless networks.

                Mesh Node

                A mesh node is defined as a physical or logical entity
                in the mesh network participating in forming the mesh
                backhaul. There are two types of mesh nodes supported
                in Cisco mesh network:RAP and MAP.

                Root AP (RAP)

                The AP forming the bridge between a wired and a mesh
                network with an Ethernet interface to the wired
                network and a 802.11 radio interface to the mesh
                network

                Mesh AP (MAP).

                The AP extending wireless coverage similar to a
                repeater in a mesh network and consists of a 802.11
                uplink and a 802.11 downlink. On a single-radio
                backhaul, both uplink and downlink exist on the same
                radio and are logical links only. On a multi-radio
                backhaul, they may exist on different radios.MAP APs
                associates directly with RAP APs or with another MAP
                AP. Each association of AP (MAP-MAP or RAP-MAP) with
                another AP forms parent-child relationship.

                Mesh Network

                Network starting with the wireless backhaul downlink
                of the RAP and all the entities below except any
                attached network to the Ethernet link of MAPs. A mesh
                network below a single RAP is also referred to as a
                'Mesh Sector'.A mesh network consists of mesh nodes.
                A single mesh network is always augmented to a single
                wired network.

                Mesh Link

                A logical 802.11 link between two mesh nodes. A single
                link is point-to-point. All point-to-multipoint links
                are considered as multiple mesh links. Often referred
                to as mesh backhaul link.

                Mesh Backhaul

                A Mesh backhaul consists of mesh nodes and mesh links
                terminating at a RAP. This necessarily creates a one-
                to-one relationship between a 'mesh network', 'mesh
                sector' and a 'mesh backhaul' where these terms can be
                used interchangeably.

                SNR
                Signal to Noise ratio on the 802.11 radio.

                Bridged network
                The bridged network is defined as the network(s)
                attached to the Ethernet port of any MAP. There can be
                multiple such networks attached to a single mesh
                network.

                REFERENCE

                [1] Wireless LAN Medium Access Control ( MAC ) and
                Physical Layer ( PHY ) Specifications.

                [2] Draft-obara-capwap-lwapp-00.txt, IETF Light
                Weight Access Point Protocol "

        REVISION      "200604100000Z"
        DESCRIPTION
                "Initial version of this MIB module. "
        ::= { ciscoLwappDot11ClientCcxMIBObjects 3 }

ciscoLwappDot11CcxClientMIBObjects  OBJECT IDENTIFIER
        ::={ ciscoLwappDot11CcxClientMIB 0 }

ciscoClientCcxEventLogRequest OBJECT IDENTIFIER
	::={ ciscoLwappDot11CcxClientMIBObjects 1 }

ciscoClientCcxEventLogResponse OBJECT IDENTIFIER
	::={ ciscoLwappDot11CcxClientMIBObjects 2 }

ciscoClientCcxEventLogStatus OBJECT IDENTIFIER
	::={ ciscoLwappDot11CcxClientMIBObjects 3 }

ciscoClientCcxStatsRequest OBJECT IDENTIFIER
	::={ ciscoLwappDot11CcxClientMIBObjects 4 }

ciscoClientCcxStatsResponse OBJECT IDENTIFIER
	::={ ciscoLwappDot11CcxClientMIBObjects 5 }


CcxEventLogResponseStatus ::= TEXTUAL-CONVENTION

	STATUS    current
	DESCRIPTION
		"This attribute represents the response of the ccx
	       	event log request."
	SYNTAX INTEGER {
		ccx-event-log-successful (1),
		ccx-event-log-refused (2),
		ccx-event-log-incapable (3)
	}

CcxEventLogDialogToken ::= TEXTUAL-CONVENTION

	STATUS    current
	DESCRIPTION
		"This attribute represents the token generated for the
	       	request sent to a client."
	SYNTAX Unsigned32


cldccEventLogsRequestTable OBJECT-TYPE

       SYNTAX     SEQUENCE OF CldccEventLogsRequestEntry
       MAX-ACCESS not-accessible
       STATUS     current
       DESCRIPTION
		  "This table contains list of clients to which the event log
		  request has been sent for fetching the logs. The table
                  has a column corresponding to the type of logs to be fetched
		  for each client.The current logs supported are Roaming,
		  RSNA and Syslog."

::= { ciscoClientCcxEventLogRequest 1 }

cldccEventLogsRequestEntry OBJECT-TYPE

        SYNTAX        CldccEventLogsRequestEntry
        MAX-ACCESS    not-accessible
        STATUS        current
        DESCRIPTION
                      "There is an entry in the table where entry is identified
                      by the client Mac address."
        INDEX
	{
         cldcClientMacAddress
	}

::= { cldccEventLogsRequestTable 1 }

CldccEventLogsRequestEntry::=

         SEQUENCE
         {
              cldccEventLogsRequestLogType      BITS,
              cldccEventLogsRequestRowStatus	RowStatus
         }

cldccEventLogsRequestLogType    OBJECT-TYPE

         SYNTAX  BITS {
                      roaming(0),
                      rsna(1),
                      syslog(2)
                    }
         MAX-ACCESS read-write
	 STATUS     current
         DESCRIPTION
		   "This is the type of the logs which is required from
                   the client.This can be Roaming,RSNA or Syslogs."

::= { cldccEventLogsRequestEntry 1 }


cldccEventLogsRequestRowStatus OBJECT-TYPE

         SYNTAX     RowStatus
         MAX-ACCESS read-create
         STATUS     current
         DESCRIPTION
                "This field is used to add/remove entries from this
                table.To add a row in this table, createAndGo
                row status will be used."

::= { cldccEventLogsRequestEntry 2}


cldccSysLogsTable OBJECT-TYPE

        SYNTAX      SEQUENCE OF CldccSysLogsEntry
        MAX-ACCESS  not-accessible
        STATUS       current
        DESCRIPTION
		   "This table contains Sys logs of the various
		   ccxv5 clients."

::= { ciscoClientCcxEventLogResponse 1 }

cldccSysLogsEntry OBJECT-TYPE

        SYNTAX      CldccSysLogsEntry
        MAX-ACCESS  not-accessible
        STATUS      current
        DESCRIPTION
		"There is an entry in the table for each entry
	       	identified by the client mac address and dialog
		token."
        INDEX
	{
        cldcClientMacAddress,
	cldccSysLogsIndex
        }

::= { cldccSysLogsTable 1 }

CldccSysLogsEntry ::=

        SEQUENCE  {
              cldccSysLogsIndex  Unsigned32,
              cldccSysLogsTimeStamp  TimeStamp,
              cldccSysLogsBuffer     OCTET STRING
        }

cldccSysLogsIndex OBJECT-TYPE

       SYNTAX        Unsigned32
       MAX-ACCESS    not-accessible
       STATUS        current
       DESCRIPTION
                    "This object stores the dialog token
		    exchanged between client and controller
		    for the give sys log request."

::= { cldccSysLogsEntry 1 }


cldccSysLogsTimeStamp OBJECT-TYPE

       SYNTAX        TimeStamp
       MAX-ACCESS    read-only
       STATUS        current
       DESCRIPTION
                    "This object stores the time stamp when the
		    syslog messages were generated."

::= { cldccSysLogsEntry 3 }

cldccSysLogsBuffer OBJECT-TYPE

       SYNTAX        OCTET STRING ( SIZE(256) )
       MAX-ACCESS    read-only
       STATUS        current
       DESCRIPTION
                    "This stores the syslog messages generated on
		    the client side."

::= { cldccSysLogsEntry 4 }


cldccRoamingLogsTable OBJECT-TYPE

  SYNTAX        SEQUENCE OF CldccRoamingLogsEntry
  MAX-ACCESS 	not-accessible
  STATUS     	current
  DESCRIPTION
		"This table contains Roaming logs of the clients."

  ::= { ciscoClientCcxEventLogResponse 2}

cldccRoamingLogsEntry OBJECT-TYPE
    SYNTAX      CldccRoamingLogsEntry
    MAX-ACCESS 	not-accessible
    STATUS     	current
    DESCRIPTION
		"There is an entry in the table for where each entry
		is identified by the client mac address and dialog
		token."
    INDEX {
	   cldcClientMacAddress,
           cldccRoamingLogsIndex
	  }

::= { cldccRoamingLogsTable 1 }

CldccRoamingLogsEntry ::=
	SEQUENCE  {
          cldccRoamingLogsIndex		  Unsigned32,
          cldccRoamingLogsTimeStamp         TimeStamp,
          cldccRoamingLogsTargetSSID   	  MacAddress,
          cldccRoamingLogsSourceSSID	  MacAddress,
          cldccRoamingLogsTransitionTime    CiscoMilliSeconds,
          cldccRoamingLogsTransitionReason  INTEGER,
          cldccRoamingLogsTransitionResult  INTEGER
	}

cldccRoamingLogsIndex OBJECT-TYPE

  SYNTAX        Unsigned32
  MAX-ACCESS 	read-only
  STATUS     	current
  DESCRIPTION
		"This is the index of the roaming logs."

::= { cldccRoamingLogsEntry 1 }

cldccRoamingLogsTimeStamp   OBJECT-TYPE

  SYNTAX        TimeStamp
  MAX-ACCESS 	read-only
  STATUS     	current
  DESCRIPTION
		"This is the time stamp of the log."

::= { cldccRoamingLogsEntry 2 }


cldccRoamingLogsTargetSSID  OBJECT-TYPE

    SYNTAX        MacAddress
    MAX-ACCESS 	  read-only
    STATUS     	  current
    DESCRIPTION
		"This is the BSSID of the AP that is target of the
		attempted transition."

    ::= { cldccRoamingLogsEntry 3 }

cldccRoamingLogsSourceSSID   OBJECT-TYPE

    SYNTAX       MacAddress
    MAX-ACCESS 	 read-only
    STATUS       current
    DESCRIPTION
	      "This is the BSSID of the associated AP prior to
	      transition."

::= { cldccRoamingLogsEntry  4 }


cldccRoamingLogsTransitionTime OBJECT-TYPE

    SYNTAX     CiscoMilliSeconds
    MAX-ACCESS read-only
    STATUS     current
    DESCRIPTION
	       "This is the difference from last time a frame could have
	       been transmitted on the source BSS to the time when a
	       non-802.1x data frame can be attempted on the target BSS."

::= { cldccRoamingLogsEntry  5 }


cldccRoamingLogsTransitionReason  OBJECT-TYPE

    SYNTAX    INTEGER
    {
     normal-roam-poor-link(1),
     normal-roam-load-bal(2),
     insufficient-capacity(3),
     inf-directed-roam(4),
     first-association-to-wlan(5),
     roaming-from-cellular(6),
     roaming-to-cellular(7),
     normal-roam-better-ap(8),
     disassociated-or-deauthenticated(9),
     failed-8021x-eap-auth(10),
     failed-8021x-4way-handshake(11),
     many-replay-counters(12),
     many-data-mic-failures(13),
     many-mgt-mic-failures(14),
     max-retransmissions-excedded(15),
     excessive-interference(16),
     many-broadcast-disassociations(17),
     many-broadcast-deauth(18)
    }
 MAX-ACCESS 	read-only
 STATUS     	current
 DESCRIPTION
		"This field indicates the reason why a transition attempt occurred."
::= { cldccRoamingLogsEntry  6 }


cldccRoamingLogsTransitionResult  OBJECT-TYPE

  SYNTAX       INTEGER (0..51)
  MAX-ACCESS   read-only
  STATUS       current
  DESCRIPTION
	     "This field shows the results of the attempted transition."

  ::= { cldccRoamingLogsEntry   7 }


cldccRsnaDataTable OBJECT-TYPE

  SYNTAX        SEQUENCE OF CldccRsnaDataEntry
  MAX-ACCESS 	not-accessible
  STATUS     	current
  DESCRIPTION
		"This table contains Rsna data logs of the clients."

  ::= { ciscoClientCcxEventLogResponse 3 }


cldccRsnaDataEntry OBJECT-TYPE

    SYNTAX    CldccRsnaDataEntry
    MAX-ACCESS 	not-accessible
    STATUS     	current
    DESCRIPTION
		"There is an entry in the table for where each entry
		is identified by the client mac address and dialog
		token."
    INDEX {
	   cldcClientMacAddress,
           cldccRsnaDataIndex
	  }

::= { cldccRsnaDataTable 1 }

CldccRsnaDataEntry ::=
	SEQUENCE  {
          cldccRsnaDataIndex 	 Unsigned32,
          cldccRsnaDataTimeStamp  TimeStamp,
          cldccRsnaDataVersion    Unsigned32,
          cldccRsnaDataTargetSSID    MacAddress,
          cldccRsnaDataAuthType	  INTEGER,
          cldccRsnaDataResult    INTEGER,
          cldccRsnaDataElemMultiCastOuis OCTET STRING,
          cldccRsnaDataElemUnicastCastOuis OCTET STRING,
          cldccRsnaDataElemAuthOuis OCTET STRING,
          cldccRsnaDataElemCapabilities Unsigned32
	}

cldccRsnaDataIndex OBJECT-TYPE

    SYNTAX       Unsigned32
    MAX-ACCESS 	 not-accessible
    STATUS     	 current
    DESCRIPTION
		"This is the index of the Rsna Data."

    ::= { cldccRsnaDataEntry 1 }

cldccRsnaDataTimeStamp OBJECT-TYPE

       SYNTAX        TimeStamp
       MAX-ACCESS    read-only
       STATUS        current
       DESCRIPTION
                    "This object stores the time stamp when the
		    rsna data were generated."

::= { cldccRsnaDataEntry 2 }

cldccRsnaDataVersion OBJECT-TYPE

    SYNTAX        Unsigned32
    MAX-ACCESS 	  read-only
    STATUS     	  current
    DESCRIPTION
		"This is the RSNA Data Version."

    ::= { cldccRsnaDataEntry 3 }

cldccRsnaDataTargetSSID OBJECT-TYPE

    SYNTAX        MacAddress
    MAX-ACCESS 	  read-only
    STATUS     	  current
    DESCRIPTION
		"This is the BSSID of the AP that is targeted."

    ::= { cldccRsnaDataEntry 4 }


cldccRsnaDataAuthType OBJECT-TYPE

SYNTAX  INTEGER
 {
ccx-dot1x-leap (0),
ccx-dot1x-eap-fast (1),
ccx-dot1x-eap-tls (2),
ccx-dot1x-eap-ttls (3),
ccx-dot1x-peap-v0 (4),
ccx-dot1x-peap-v1 (5),
ccx-dot1x-eap-md5 (6),
ccx-dot1x-eap-sim (7),
ccx-dot1x-psk (8),
ccx-dot1x-unknown (255)
}
  MAX-ACCESS   read-only
  STATUS       current
  DESCRIPTION
	     "This attribute represents the authentication type
	     used."

  ::= { cldccRsnaDataEntry 5 }

cldccRsnaDataResult OBJECT-TYPE

  SYNTAX       INTEGER (0..255)
  MAX-ACCESS   read-only
  STATUS       current
  DESCRIPTION
	     "This attribute stores the result of the RSNA Data."

  ::= { cldccRsnaDataEntry 6 }


cldccRsnaDataElemMultiCastOuis OBJECT-TYPE

  SYNTAX       OCTET STRING ( SIZE(0..256) )
  MAX-ACCESS   read-only
  STATUS       current
  DESCRIPTION
	     "This attribute represents the multicast ouis
	     of a RSNA element."

  ::= { cldccRsnaDataEntry 7 }

cldccRsnaDataElemUnicastCastOuis OBJECT-TYPE

  SYNTAX       OCTET STRING ( SIZE(0..256) )
  MAX-ACCESS   read-only
  STATUS       current
  DESCRIPTION
	     "This field represents the unicast ouis
	     of a RSNA element."

  ::= { cldccRsnaDataEntry 8 }

cldccRsnaDataElemAuthOuis OBJECT-TYPE

  SYNTAX       OCTET STRING ( SIZE(0..256) )
  MAX-ACCESS   read-only
  STATUS       current
  DESCRIPTION
	     "This field represents the auth ouis
	     of a RSNA element."

  ::= { cldccRsnaDataEntry 9 }

cldccRsnaDataElemCapabilities OBJECT-TYPE

  SYNTAX       Unsigned32
  MAX-ACCESS   read-only
  STATUS       current
  DESCRIPTION
	     "This field represents the
	    capabilities of the RSNA element ."

  ::= { cldccRsnaDataEntry 10 }


cldccStatsReqTable OBJECT-TYPE

  SYNTAX        SEQUENCE OF CldccStatsReqEntry
  MAX-ACCESS 	not-accessible
  STATUS     	current
  DESCRIPTION
               "This table contains the stats req for the
               ccx clients."

  ::= {ciscoClientCcxStatsRequest 1 }

cldccStatsReqEntry OBJECT-TYPE

        SYNTAX        CldccStatsReqEntry
        MAX-ACCESS    not-accessible
        STATUS        current
        DESCRIPTION
                      "There is an entry in the table where entry
		      is identified by the client Mac address."
        INDEX
	{
         cldcClientMacAddress
	}

::= { cldccStatsReqTable 1 }

CldccStatsReqEntry::=

         SEQUENCE
         {
              cldccStatsReqStatus  INTEGER,
              cldccStatsReqGroupId INTEGER,
              cldccStatsReqDuration CiscoMilliSeconds,
              cldccStatsReqRowStatus RowStatus
         }

cldccStatsReqStatus OBJECT-TYPE

        SYNTAX        INTEGER
			{
                         incapable(0),
                         refused(1),
                         invalid-state(2),
                         failure(3),
                         success(4),
                         inprogress(5)
			}
        MAX-ACCESS    read-write
        STATUS        current
        DESCRIPTION
                      "There is an entry in the table where entry
		      is identified by the client Mac address."

::= { cldccStatsReqEntry 1 }

cldccStatsReqGroupId OBJECT-TYPE

        SYNTAX        INTEGER
			{
                         dot11-meas(0),
                         security-meas(1)
			}
        MAX-ACCESS    read-write
        STATUS        current
        DESCRIPTION
                      "There is an entry in the table where entry
		      is identified by the client Mac address."

::= { cldccStatsReqEntry 2 }


cldccStatsReqDuration OBJECT-TYPE

         SYNTAX     CiscoMilliSeconds
         MAX-ACCESS read-write
         STATUS     current
         DESCRIPTION
                "This field represents the duration of the
	       	measurement."

::= { cldccStatsReqEntry 3 }

cldccStatsReqRowStatus OBJECT-TYPE

         SYNTAX     RowStatus
         MAX-ACCESS read-create
         STATUS     current
         DESCRIPTION
                "This field is used to add/remove entries from this
                table.To add a row in this table, createAndGo
                row status will be used."

::= { cldccStatsReqEntry 4 }


cldccStatsDot11RespTable OBJECT-TYPE

  SYNTAX        SEQUENCE OF CldccStatsDot11RespEntry
  MAX-ACCESS 	not-accessible
  STATUS     	current
  DESCRIPTION
               "This table contains the stats response for the
               ccx clients."

  ::= {ciscoClientCcxStatsResponse 1 }

cldccStatsDot11RespEntry OBJECT-TYPE

        SYNTAX        CldccStatsDot11RespEntry
        MAX-ACCESS    not-accessible
        STATUS        current
        DESCRIPTION
                      "There is an entry in the table where entry
                       is identified by the client Mac address."
        INDEX
	{
	  cldcClientMacAddress
	}

::= { cldccStatsDot11RespTable 1 }


CldccStatsDot11RespEntry::=

         SEQUENCE
         {
           cldccStatsRespTransmittedFragmentCount Counter32,
           cldccStatsRespMulticastTransmittedFrameCount Counter32,
           cldccStatsRespFailedCount Counter32,
           cldccStatsRespRetryCount Counter32,
           cldccStatsRespMultipleRetryCount Counter32,
           cldccStatsRespFrameDuplicateCount Counter32,
           cldccStatsRespRtsSuccessCount Counter32,
           cldccStatsRespRtsFailureCount Counter32,
           cldccStatsRespAckFailureCount Counter32,
           cldccStatsRespReceivedFragmentCount Counter32,
           cldccStatsRespMulticastReceivedFrameCount Counter32,
           cldccStatsRespFcsErrorCount Counter32,
           cldccStatsRespTransmittedFrameCount Counter32
         }

cldccStatsRespTransmittedFragmentCount OBJECT-TYPE

         SYNTAX     Counter32
         MAX-ACCESS read-only
         STATUS     current
         DESCRIPTION
                "This field represents the transmitted fragment
	       	count."

::= { cldccStatsDot11RespEntry  1 }

cldccStatsRespMulticastTransmittedFrameCount OBJECT-TYPE

         SYNTAX     Counter32
         MAX-ACCESS read-only
         STATUS     current
         DESCRIPTION
                "This field represents the multicast
	       	transmitted frame count."

::= { cldccStatsDot11RespEntry  2 }

cldccStatsRespFailedCount OBJECT-TYPE

         SYNTAX     Counter32
         MAX-ACCESS read-only
         STATUS     current
         DESCRIPTION
                "This field represents the failed count."

::= { cldccStatsDot11RespEntry  3 }


cldccStatsRespRetryCount OBJECT-TYPE

         SYNTAX     Counter32
         MAX-ACCESS read-only
         STATUS     current
         DESCRIPTION
                "This field represents the duplicate frame
	       	count."

::= { cldccStatsDot11RespEntry  4 }

cldccStatsRespMultipleRetryCount OBJECT-TYPE

         SYNTAX     Counter32
         MAX-ACCESS read-only
         STATUS     current
         DESCRIPTION
                "This field represents the retry
	       	count."

::= { cldccStatsDot11RespEntry  5 }


cldccStatsRespFrameDuplicateCount OBJECT-TYPE

         SYNTAX     Counter32
         MAX-ACCESS read-only
         STATUS     current
         DESCRIPTION
                "This field represents the duplicate frame
	       	count."

::= { cldccStatsDot11RespEntry  6 }

cldccStatsRespRtsSuccessCount OBJECT-TYPE

         SYNTAX     Counter32
         MAX-ACCESS read-only
         STATUS     current
         DESCRIPTION
                "This field represents the RTS success
	       	count."

::= { cldccStatsDot11RespEntry  7 }


cldccStatsRespRtsFailureCount OBJECT-TYPE

         SYNTAX     Counter32
         MAX-ACCESS read-only
         STATUS     current
         DESCRIPTION
                "This field represents the RTS failure
	       	count."

::= { cldccStatsDot11RespEntry  8 }

cldccStatsRespAckFailureCount OBJECT-TYPE

         SYNTAX     Counter32
         MAX-ACCESS read-only
         STATUS     current
         DESCRIPTION
                "This field represents the ack failure
	       	count."

::= { cldccStatsDot11RespEntry  9 }

cldccStatsRespReceivedFragmentCount OBJECT-TYPE

         SYNTAX     Counter32
         MAX-ACCESS read-only
         STATUS     current
         DESCRIPTION
                "This field represents the received fragment
	       	count."

::= { cldccStatsDot11RespEntry  10 }

cldccStatsRespMulticastReceivedFrameCount OBJECT-TYPE

         SYNTAX     Counter32
         MAX-ACCESS read-only
         STATUS     current
         DESCRIPTION
                "This field represents the multicast received
	       	frame count."

::= { cldccStatsDot11RespEntry  11 }

cldccStatsRespFcsErrorCount OBJECT-TYPE

         SYNTAX     Counter32
         MAX-ACCESS read-only
         STATUS     current
         DESCRIPTION
                "This field represents the fcs error
	       	count."

::= { cldccStatsDot11RespEntry  12 }

cldccStatsRespTransmittedFrameCount OBJECT-TYPE

         SYNTAX     Counter32
         MAX-ACCESS read-only
         STATUS     current
         DESCRIPTION
                "This field represents the transmitted frame
	       	count."

::= { cldccStatsDot11RespEntry  13 }


cldccStatsSecurityRespTable OBJECT-TYPE

  SYNTAX        SEQUENCE OF CldccStatsSecurityRespEntry
  MAX-ACCESS 	not-accessible
  STATUS     	current
  DESCRIPTION
               "This table contains the stats response for the
               ccx clients."

  ::= {ciscoClientCcxStatsResponse 2 }

cldccStatsSecurityRespEntry OBJECT-TYPE

        SYNTAX        CldccStatsSecurityRespEntry
        MAX-ACCESS    not-accessible
        STATUS        current
        DESCRIPTION
                      "There is an entry in the table where entry
                       is identified by the client Mac address."
        INDEX
	{
		cldcClientMacAddress
	}

::= { cldccStatsSecurityRespTable 1 }


CldccStatsSecurityRespEntry::=

         SEQUENCE
         {
           cldccStatsRespSelectedPairwiseCipher Counter32,
           cldccStatsRespTkipIcvErrors Counter32,
           cldccStatsRespTkipLocalMicFailures Counter32,
           cldccStatsRespCcmpReplays Counter32,
           cldccStatsRespCcmpDecrypErrors Counter32,
           cldccStatsRespTkipReplays Counter32,
           cldccStatsRespMgmtStatsTkipIcvErrors Counter32,
           cldccStatsRespMgmtStatsTkipLocalMicFailures Counter32,
           cldccStatsRespMgmtStatsCcmpReplays Counter32,
           cldccStatsRespMgmtStatsCcmpDecryptErrors Counter32,
           cldccStatsRespMgmtStatsTkipReplays Counter32,
           cldccStatsRespMgmtStatsTkipMhdrErrors Counter32,
           cldccStatsRespMgmtStatsCcmpMhdrErrors Counter32,
           cldccStatsRespMgmtStatsBroadcastDisassociateCount Counter32,
           cldccStatsRespMgmtStatsBroadcastDeauthenticateCount Counter32,
           cldccStatsRespMgmtStatsBroadcastActionFrameCount Counter32

         }

cldccStatsRespSelectedPairwiseCipher OBJECT-TYPE

         SYNTAX     Unsigned32
         MAX-ACCESS read-only
         STATUS     current
         DESCRIPTION
                "This field represents the pairwise
	       	cipher."

::= { cldccStatsSecurityRespEntry 1 }

cldccStatsRespTkipIcvErrors OBJECT-TYPE

         SYNTAX     Counter32
         MAX-ACCESS read-only
         STATUS     current
         DESCRIPTION
                "This field represents the tkip icv error
	       	count."

::= { cldccStatsSecurityRespEntry 2 }


cldccStatsRespTkipLocalMicFailures OBJECT-TYPE

         SYNTAX     Counter32
         MAX-ACCESS read-only
         STATUS     current
         DESCRIPTION
                "This field represents the local tkip
	       	mic failure count."

::= { cldccStatsSecurityRespEntry 3 }

cldccStatsRespCcmpReplays OBJECT-TYPE

         SYNTAX     Counter32
         MAX-ACCESS read-only
         STATUS     current
         DESCRIPTION
                "This field represents the ccmp replay
	       	count."

::= { cldccStatsSecurityRespEntry 4 }

cldccStatsRespCcmpDecrypErrors OBJECT-TYPE

         SYNTAX     Counter32
         MAX-ACCESS read-only
         STATUS     current
         DESCRIPTION
                "This field represents the CCMP decrypt error
	       	count."

::= { cldccStatsSecurityRespEntry 5 }

cldccStatsRespTkipReplays OBJECT-TYPE

         SYNTAX     Counter32
         MAX-ACCESS read-only
         STATUS     current
         DESCRIPTION
                "This field represents the tkip replay
	       	count."

::= { cldccStatsSecurityRespEntry  6}

cldccStatsRespMgmtStatsTkipIcvErrors OBJECT-TYPE

         SYNTAX     Counter32
         MAX-ACCESS read-only
         STATUS     current
         DESCRIPTION
                "This field represents the tkip icv error
	       	count."

::= { cldccStatsSecurityRespEntry 7 }

cldccStatsRespMgmtStatsTkipLocalMicFailures OBJECT-TYPE

         SYNTAX     Counter32
         MAX-ACCESS read-only
         STATUS     current
         DESCRIPTION
                "This field represents the tkip local mic failure
	       	count."

::= { cldccStatsSecurityRespEntry 8}


cldccStatsRespMgmtStatsCcmpReplays OBJECT-TYPE

         SYNTAX     Counter32
         MAX-ACCESS read-only
         STATUS     current
         DESCRIPTION
                "This field represents the CCMP replay
	       	count."

::= { cldccStatsSecurityRespEntry 9}

cldccStatsRespMgmtStatsCcmpDecryptErrors OBJECT-TYPE

         SYNTAX     Counter32
         MAX-ACCESS read-only
         STATUS     current
         DESCRIPTION
                "This field represents the Ccmp decrypt error
	       	count."

::= { cldccStatsSecurityRespEntry 10}


cldccStatsRespMgmtStatsTkipReplays OBJECT-TYPE

         SYNTAX     Counter32
         MAX-ACCESS read-only
         STATUS     current
         DESCRIPTION
                "This field represents the tkip replay
	       	count."

::= { cldccStatsSecurityRespEntry 11}

cldccStatsRespMgmtStatsTkipMhdrErrors OBJECT-TYPE

         SYNTAX     Counter32
         MAX-ACCESS read-only
         STATUS     current
         DESCRIPTION
                "This field represents the tkip mhdr error
	       	count."

::= { cldccStatsSecurityRespEntry 12}

cldccStatsRespMgmtStatsCcmpMhdrErrors OBJECT-TYPE

         SYNTAX     Counter32
         MAX-ACCESS read-only
         STATUS     current
         DESCRIPTION
                "This field represents the Ccmp Mhdr error
                count."

::= { cldccStatsSecurityRespEntry 13 }

cldccStatsRespMgmtStatsBroadcastDisassociateCount OBJECT-TYPE

         SYNTAX     Counter32
         MAX-ACCESS read-only
         STATUS     current
         DESCRIPTION
                "This field represents the broadcast disassociate
	       	count."

::= { cldccStatsSecurityRespEntry 14 }


cldccStatsRespMgmtStatsBroadcastDeauthenticateCount OBJECT-TYPE

         SYNTAX     Counter32
         MAX-ACCESS read-only
         STATUS     current
         DESCRIPTION
                "This field represents the broadcast deauthenticate
	       	count."

::= { cldccStatsSecurityRespEntry 15 }

cldccStatsRespMgmtStatsBroadcastActionFrameCount OBJECT-TYPE

         SYNTAX     Counter32
         MAX-ACCESS read-only
         STATUS     current
         DESCRIPTION
                "This field represents the broadcast action frame
	       	count."

::= { cldccStatsSecurityRespEntry 16 }

cldccEventLogStatusTable OBJECT-TYPE

        SYNTAX      SEQUENCE OF CldccEventLogStatusEntry
        MAX-ACCESS  not-accessible
        STATUS       current
        DESCRIPTION
		   "This table contains response status of the various
		   event log requests sent from the controller."

::= { ciscoClientCcxEventLogStatus 1 }


cldccEventLogStatusEntry OBJECT-TYPE

        SYNTAX      CldccEventLogStatusEntry
        MAX-ACCESS  not-accessible
        STATUS      current
        DESCRIPTION
		"There is an entry in the table for each entry
	       	identified by the client mac address."
        INDEX
	{
        cldcClientMacAddress
        }

::= { cldccEventLogStatusTable 1 }

CldccEventLogStatusEntry ::=

        SEQUENCE  {
              cldccRoamingLogsResponseStatus  CcxEventLogResponseStatus,
              cldccRsnaLogsResponseStatus   CcxEventLogResponseStatus,
              cldccSysLogsResponseStatus   CcxEventLogResponseStatus
        }

cldccRoamingLogsResponseStatus OBJECT-TYPE

        SYNTAX     CcxEventLogResponseStatus
        MAX-ACCESS read-only
        STATUS     current
        DESCRIPTION
		   "This is the status of roaming log request."

::= { cldccEventLogStatusEntry 1 }

cldccRsnaLogsResponseStatus OBJECT-TYPE

        SYNTAX     CcxEventLogResponseStatus
        MAX-ACCESS read-only
        STATUS     current
        DESCRIPTION
		   "This is the status of rsna log request."

::= { cldccEventLogStatusEntry 2 }

cldccSysLogsResponseStatus   OBJECT-TYPE

        SYNTAX     CcxEventLogResponseStatus
        MAX-ACCESS read-only
        STATUS     current
        DESCRIPTION
                  "This is the status of sys log request."

::= { cldccEventLogStatusEntry 3 }

END
