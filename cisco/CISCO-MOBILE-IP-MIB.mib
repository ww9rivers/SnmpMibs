-- *****************************************************************
-- CISCO-MOBILE-IP-MIB.my: Cisco Enterprise Mobile IP MIB file
--
-- July 2000, Ravindra Rathi
--
-- Copyright (c) 2000-2005, 2008-2009 by Cisco Systems Inc.
-- All rights reserved.
--
-- *****************************************************************

CISCO-MOBILE-IP-MIB DEFINITIONS ::= BEGIN

IMPORTS
    MODULE-IDENTITY,
    OBJECT-TYPE,
    NOTIFICATION-TYPE,
    Gauge32,
    Counter32,
    Integer32,
    IpAddress,
    Unsigned32,
    Counter64
        FROM SNMPv2-SMI
    MODULE-COMPLIANCE,
    OBJECT-GROUP,
    NOTIFICATION-GROUP
        FROM SNMPv2-CONF
    RowStatus,
    TimeInterval,
    TimeStamp,
    DateAndTime,
    TruthValue,
    MacAddress,
    TEXTUAL-CONVENTION
        FROM SNMPv2-TC
    RegistrationFlags,
    haMobilityBindingEntry,
    mnRegistrationEntry,
    faCOAEntry,
    mnHAEntry,
    mnState,
    mnRegCOA,
    mnRegAgentAddress
        FROM MIP-MIB
    InetAddressType,
    InetAddress,
    InetAddressPrefixLength
        FROM INET-ADDRESS-MIB
    ZeroBasedCounter32
        FROM RMON2-MIB
    SnmpAdminString
        FROM SNMP-FRAMEWORK-MIB
    ifIndex,
    InterfaceIndex,
    InterfaceIndexOrZero
        FROM IF-MIB
    CounterBasedGauge64
        FROM HCNUM-TC
    ciscoMgmt
        FROM CISCO-SMI;


ciscoMobileIpMIB MODULE-IDENTITY
    LAST-UPDATED    "200906260000Z"
    ORGANIZATION    "Cisco Systems, Inc."
    CONTACT-INFO
            "Cisco Systems
            Customer Service

            Postal: 170 W. Tasman Drive
            San Jose, CA  95134
            USA

            Tel: +1 800 553-NETS

            E-mail: cs-mobileip@cisco.com"
    DESCRIPTION
        "An extension to the IETF MIB module defined in
        RFC-2006 for managing Mobile IP implementations.

        Mobile IP introduces the following new functional
        entities:

        Mobile Node(MN)
           A host or router that changes its point of
           attachment from one network or subnetwork to
           another. A mobile node may change its location
           without changing its IP address; it may continue to
           communicate with other Internet nodes at any
           location using its (constant) IP address, assuming
           link-layer connectivity to a point of attachment is
           available.

        Home Agent(HA)
           A router on a mobile node's home network which
           tunnels datagrams for delivery to the mobile node
           when it is away from home, and maintains current
           location information for the mobile node.

        Foreign Agent(FA)
           A router on a mobile node's visited network which
           provides routing services to the mobile node while
           registered. The foreign agent detunnels and delivers
           datagrams to the mobile node that were tunneled by
           the mobile node's home agent. For datagrams sent by
           a mobile node, the foreign agent may serve as a
           default router for registered mobile nodes.

        Mobile Router(MR)
           A mobile node that is a router. It provides for the
           mobility for one or more networks moving together.
           The nodes connected to the network server by the
           mobile router may themselves be fixed nodes, mobile
           nodes or routers.

        Mobile Network
           Network that moves with the mobile router.

        Following is the terminology associated with Mobile IP
        protocol:

        Agent Advertisement
           An advertisement message constructed by attaching a
           special Extension to a router advertisement message.

        Care-of Address (CoA)
           The termination point of a tunnel toward a mobile
           node, for datagrams forwarded to the mobile node
           while it is away from home. The protocol can use
           two different types of care-of address: a 'foreign
           agent care-of address' is an address of a foreign
           agent with which the mobile node is registered, and
           a 'co-located care-of address' (CCoA) is an
           externally obtained local address which the mobile
           node has associated with one of its own network
           interfaces.

        Correspondent Node
           A peer with which a mobile node is communicating.
           A correspondent node may be either mobile or
           stationary.

        Foreign Network
           Any network other than the mobile node's Home
           Network.

        Home Address
           An IP address that is assigned for an extended
           period of time to a mobile node. It remains
           unchanged regardless of where the node is attached
           to the Internet.

        Home Network
           A network, possibly virtual, having a network prefix
           matching that of a mobile node's home address. Note
           that standard IP routing mechanisms will deliver
           datagrams destined to a mobile node's Home Address
           to the mobile node's Home Network.

        Mobility Agent
           Either a home agent or a foreign agent.

        Mobility Binding
           The association of a home address with a care-of
           address, along with the remaining lifetime of that
           association.

        Mobility Security Association
           A collection of security contexts, between a pair
           of nodes, which may be applied to Mobile IP protocol
           messages exchanged between them. Each context
           indicates an authentication algorithm and mode, a
           secret (a shared key, or appropriate public/private
           key pair), and a style of replay protection in use.

        Node
           A host or a router.

        Nonce
           A randomly chosen value, different from previous
           choices, inserted in a message to protect against
           replays.

        Security Parameter Index (SPI)
           An index identifying a security context between a
           pair of nodes among the contexts available in the
           Mobility Security Association. SPI values 0 through
           255 are reserved and MUST NOT be used in any
           Mobility Security Association.

        Tunnel
           The path followed by a datagram while it is
           encapsulated. The model is that, while it is
           encapsulated, a datagram is routed to a
           knowledgeable decapsulating agent, which
           decapsulates the datagram and then correctly
           delivers it to its ultimate destination.

        Visited Network
           A network other than a mobile node's Home Network,
           to which the mobile node is currently connected.

        Visitor List
           The list of mobile nodes visiting a foreign agent.

        Keyed Hashing for Message Authentication (HMAC)
           A mechanism for message authentication using
           cryptographic hash functions. HMAC can be used with
           any iterative cryptographic hash function, e.g.,
           MD5, SHA-1, in combination with a secret shared
           key.

        The following support services are defined for
        Mobile IP:

        Agent Discovery
           Home agents and foreign agents may advertise their
           availability on each link for which they provide
           service. A newly arrived mobile node can send a
           solicitation on the link to learn if any prospective
           agents are present.

        Registration
           When the mobile node is away from home, it registers
           its care-of address with its home agent. Depending
           on its method of attachment, the mobile node will
           register either directly with its home agent, or
           through a foreign agent which forwards the
           registration to the home agent.

        Following is the terminology associated with the home
        agent redundancy feature:

        Peer Home Agent
           Active home agent and standby home agent are peers
           to each other.

        Binding Update
           A binding update contains the registration request
        information. The home agent sends the update to its
        peer after accepting a registration.

        Binding Information
           Binding information contains the entries in the
        mobility binding table. The home agent sends a binding
        information request to its peer to retrieve all
        mobility bindings for a specified home agent address.

        3GPP2
                3rd Generation Partnership Project 2. This is
        the standardization group for CDMA2000, the set of 3G
        standards based on earlier 2G CDMA technology.

        WiMAX
                Worldwide Interoperability for Microwave Access,
         Inc. (group promoting IEEE 802.16 wireless broadband
         standard)

        MIP
                Mobile IP

        This MIB is organized as described below:

           The IETF Mobile IP MIB module [RFC-2006] has six
           main groups. Three of them represent the Mobile IP
           entities i.e. 'MipFA': foreign agent, 'MipHA':
           home agent and 'MipMN': mobile node. Each of these
           groups have been further subdivided into different
           subgroups. Each of these subgroups is a collection
           of objects related to a particular function,
           performed by the entity represented by its main
           group e.g. 'faRegistration' is a subgroup under
           group 'MipFA' which has collection of objects for
           registration function within a foreign agent. This
           MIB also follows the same hierarchical structure to
           maintain the modularity with respect to Mobile IP."
    REVISION        "200906260000Z"
    DESCRIPTION
        "Added cmiHaRegTunnelStatsTable

        The following objects has been added to cmiHaReg.

        [1] cmiHaRegIntervalSize
        [2] cmiHaRegIntervalMaxActiveBindings
        [3] cmiHaRegInterval3gpp2MaxActiveBindings
        [4] cmiHaRegIntervalWimaxMaxActiveBindings

        The following object groups has been added to
        ciscoMobileIpGroups.

        [1] ciscoMobileIpHaRegIntervalStatsGroup
        [2] ciscoMobileIpHaRegTunnelStatsGroup

        The MODULE-COMPLIANCE ciscoMobileIpComplianceRev1 has been
        deprecated by ciscoMobileIpComplianceRev2."
    REVISION        "200901220000Z"
    DESCRIPTION
        "The following objects have been added
        [1] cmiHaMaximumBindings
        [2] cmiHaSystemVersion

        The following notifications have been added
        [1] cmiHaMaxBindingsNotif

        The Object cmiTrapControl has been modified to include
        a new bit for cmiHaMaxBindingsNotif.

        The following object-groups have been added
        [1] ciscoMobileIpHaRegGroupV1
        [2] ciscoMobileIpMrNotificationGroupV3
        [3] ciscoMobileIpHaSystemGroupV1

        The compliance statement ciscoMobileIpComplianceV12R11
        has been deprecated by ciscoMobileIpComplianceRev1."
    REVISION        "200812110000Z"
    DESCRIPTION
        "Added a new object cmiHaRegMobilityBindingMacAddress to
        cmiHaRegMobilityBindingTable.
        Added a new object group ciscoMobileIpHaRegGroupV12R03r2Sup2 and
        a compliance group ciscoMobileIpComplianceV12R11 which
        deprecates ciscoMobileIpComplianceV12R10."
    REVISION        "200505310000Z"
    DESCRIPTION
        "Added mobile node access interface attribute objects
        and multi-path specific objects.
        Following object groups have been created for the
        objects added for multi-path:
        ciscoMobileIpHaRegGroupV12R03r2Sup1
        ciscoMobileIpHaMobNetGroupSup1
        ciscoMobileIpMrSystemGroupV3Sup1"
    REVISION        "200405280000Z"
    DESCRIPTION
        "Added Mobile router roaming interface objects -
        cmiMrIfRoamStatus, cmiMrIfRegisteredCoAType,
        cmiMrIfRegisteredCoA, cmiMrIfRegisteredMaAddrType and
        cmiMrIfRegisteredMaAddr."
    REVISION        "200401230000Z"
    DESCRIPTION
        "Added trap cmiHaMnRegReqFailed"
    REVISION        "200311270000Z"
    DESCRIPTION
        "Added objects cmiFaTotalRegRequests,
        miFaTotalRegReplies, cmiFaMnFaAuthFailures,
        cmiFaMnAAAAuthFailures, cmiHaMnHaAuthFailures,
        and cmiHaMnAAAAuthFailures."
    REVISION        "200309050000Z"
    DESCRIPTION
        "Added object cmiMrIfCCoaEnable"
    REVISION        "200306300000Z"
    DESCRIPTION
        "Added objects cmiMrIfCCoaRegistration, cmiMrIfCCoaOnly
        and cmiMrCollocatedTunnel"
    REVISION        "200301230000Z"
    DESCRIPTION
        "1. Duplicated maAdvConfigTable from MIP-MIB with the
        index changed to IfIndex instead of ip address.
        2. Deprecated cmiSecKey object and added cmSecKey2 as
        the range needs to be extended. It should accept
        strings of length 1 to 16.
        3. Added hmacMD5 type in cmiSecAlgorithmType"
    REVISION        "200211180000Z"
    DESCRIPTION
        "Added objects for Reverse tunneling, Challenge, VSEs
        and Mobile Router features."
    REVISION        "200205170000Z"
    DESCRIPTION
        "Add HA/FA initial registration,re-registration,
        de-registration counters for more granularity."
    REVISION        "200107060000Z"
    DESCRIPTION
        "Add cmiFaRegVisitorTable, cmiHaRegCounterTable,
        cmiHaRegMobilityBindingTable, cmiSecAssocTable,
        and cmiSecViolationTable. Add counters for home agent
        redundancy feature. Add performance counters for
        registration function of the mobility agents."
    REVISION        "200101250000Z"
    DESCRIPTION
        "Initial version of this MIB module."
    ::= { ciscoMgmt 174 }


ciscoMobileIpMIBObjects  OBJECT IDENTIFIER
    ::= { ciscoMobileIpMIB 1 }

-- Groups under ciscoMobileIpMIBObjects.

cmiFa  OBJECT IDENTIFIER
    ::= { ciscoMobileIpMIBObjects 1 }

cmiHa  OBJECT IDENTIFIER
    ::= { ciscoMobileIpMIBObjects 2 }

cmiSecurity  OBJECT IDENTIFIER
    ::= { ciscoMobileIpMIBObjects 3 }

cmiMa  OBJECT IDENTIFIER
    ::= { ciscoMobileIpMIBObjects 4 }

cmiMn  OBJECT IDENTIFIER
    ::= { ciscoMobileIpMIBObjects 5 }

cmiTrapObjects  OBJECT IDENTIFIER
    ::= { ciscoMobileIpMIBObjects 6 }

cmiFaReg  OBJECT IDENTIFIER
    ::= { cmiFa 1 }

cmiFaAdvertisement  OBJECT IDENTIFIER
    ::= { cmiFa 2 }

cmiFaSystem  OBJECT IDENTIFIER
    ::= { cmiFa 3 }

cmiHaReg  OBJECT IDENTIFIER
    ::= { cmiHa 1 }

cmiHaRedun  OBJECT IDENTIFIER
    ::= { cmiHa 2 }

cmiHaMobNet  OBJECT IDENTIFIER
    ::= { cmiHa 3 }

cmiHaSystem  OBJECT IDENTIFIER
    ::= { cmiHa 4 }

cmiMaReg  OBJECT IDENTIFIER
    ::= { cmiMa 1 }

cmiMaAdvertisement  OBJECT IDENTIFIER
    ::= { cmiMa 2 }

cmiMnDiscovery  OBJECT IDENTIFIER
    ::= { cmiMn 1 }

cmiMnRecentAdvReceived  OBJECT IDENTIFIER
    ::= { cmiMnDiscovery 1 }

cmiMnRegistration  OBJECT IDENTIFIER
    ::= { cmiMn 2 }

cmiMrSystem  OBJECT IDENTIFIER
    ::= { cmiMn 3 }

cmiMrDiscovery  OBJECT IDENTIFIER
    ::= { cmiMn 4 }

cmiMrRegistration  OBJECT IDENTIFIER
    ::= { cmiMn 5 }


-- Textual convention

CmiRegistrationFlags ::= TEXTUAL-CONVENTION
    STATUS          current
    DESCRIPTION
        "This data type is used to define the registration
        flags for Mobile IP registration extension:
           reverseTunnel
               -- Request to support reverse tunneling.
           gre
               -- Request to use GRE
           minEnc
               -- Request to use minimal encapsulation
           decapsulationByMN
               -- Decapsulation by mobile node
           broadcastDatagram
               -- Request to receive broadcasts
           simultaneousBindings
               -- Request to retain prior binding(s)"
    SYNTAX          BITS {
                        reverseTunnel(0),
                        gre(1),
                        minEnc(2),
                        decapsulationbyMN(3),
                        broadcastDatagram(4),
                        simultaneousBindings(5)
                    }

CmiEntityIdentifierType ::= TEXTUAL-CONVENTION
    STATUS          current
    DESCRIPTION
        "A value that represents a type of Mobile IP entity
        identifier.
        other(1)     Indicates identifier which
                     is not in one of the formats defined
                     below.

        ipaddress(2) IP address as defined by InetAddressIPv4
                     textual convention in INET-ADDRESS-MIB.

        nai(3)       A network access identifier as defined by
                     the CmiEntityIdentifier textual
                     convention."
    SYNTAX          INTEGER  {
                        other(1),
                        ipaddress(2),
                        nai(3)
                    }

CmiEntityIdentifier ::= TEXTUAL-CONVENTION
    STATUS          current
    DESCRIPTION
        "Represents the generic identifier for Mobile IP
        entities. A CmiEntityIdentifier value is always
        interpreted within the context of a
        CmiEntityIdentifierType  value.
                     Foreign agents and Home agents are
        identified by the IP addresses. Mobile nodes can be
        identified in more than one way e.g. IP addresses,
        network access identifiers (NAI). If mobile node is
        identified by  something other than IP address say by
        NAI and it gets IP address dynamically from the home
        agent then value of object of this type should be same
        as NAI. This is because then IP address is not tied
        with mobile node and it can change across registrations
        over period of time."
    SYNTAX          OCTET STRING (SIZE (1..255))

CmiSpi ::= TEXTUAL-CONVENTION
    STATUS          current
    DESCRIPTION
        "An index identifying a security context between a pair
        of nodes among the contexts available in the Mobility
        Security Association.  SPI values 0 through 255 are
        reserved and MUST NOT be used in any Mobility Security
        Association."

    REFERENCE       "RFC-2002 - IP Mobility Support, section 3.5.1"
    SYNTAX          Unsigned32 (256..4294967295)

CmiMultiPathMetricType ::= TEXTUAL-CONVENTION
    STATUS          current
    DESCRIPTION
        "An enumerated value that represents a metric type
        that is used for calculating the metric for routes
        when multiple routes are created.
        hopcount(1)  Hop count
                     Routes would be inserted with metric
                     as 1 - hop count.
        bandwidth(2) bandwidth
                     Routes would be inserted with metric
                     using the roaming interface bandwidth."
    SYNTAX          INTEGER  {
                        hopcount(1),
                        bandwidth(2)
                    }

CmiTunnelType ::= TEXTUAL-CONVENTION
    STATUS          current
    DESCRIPTION
        "This textual convention lists the tunneling protocols in use
        between a HA and CoA.

        The semantics are as follows.

                'ipinip' - This indicates that IP-in-IP protocol is in
                           use for tunnel encapsulation.

                'gre'    - This indicates that GRE protocol is in use
                           for tunnel encapsulation."
    SYNTAX          INTEGER  {
                        ipinip(1),
                        gre(2)
                    }

-- Foreign Agent Registration Group

cmiFaRegTotalVisitors OBJECT-TYPE
    SYNTAX          Gauge32
    MAX-ACCESS      read-only
    STATUS          current
    DESCRIPTION
        "The current number of entries in faVisitorTable.
        faVisitorTable contains the foreign agent's visitor
        list. The foreign agent updates this table in
        response to registration events from mobile nodes."
    REFERENCE       "RFC-2006 - Mobile IP MIB Definition using SMIv2"
    ::= { cmiFaReg 1 }
-- Foreign Agent Visitors List

cmiFaRegVisitorTable OBJECT-TYPE
    SYNTAX          SEQUENCE OF CmiFaRegVisitorEntry
    MAX-ACCESS      not-accessible
    STATUS          current
    DESCRIPTION
        "A table containing the foreign agent's visitor
        list. The foreign agent updates this table in
        response to registration events from mobile nodes.
        This table provides the same information as
        faVisitorTable of MIP-MIB. The difference is
        that indices of the table are changed so that visitors
        which are not identified by the IP address will also
        be included in the table."
    ::= { cmiFaReg 2 }

cmiFaRegVisitorEntry OBJECT-TYPE
    SYNTAX          CmiFaRegVisitorEntry
    MAX-ACCESS      not-accessible
    STATUS          current
    DESCRIPTION
        "Information for one visitor regarding registration."
    INDEX           {
                        cmiFaRegVisitorIdentifierType,
                        cmiFaRegVisitorIdentifier
                    }
    ::= { cmiFaRegVisitorTable 1 }

CmiFaRegVisitorEntry ::= SEQUENCE {
        cmiFaRegVisitorIdentifierType   CmiEntityIdentifierType,
        cmiFaRegVisitorIdentifier       CmiEntityIdentifier,
        cmiFaRegVisitorHomeAddress      IpAddress,
        cmiFaRegVisitorHomeAgentAddress IpAddress,
        cmiFaRegVisitorTimeGranted      TimeInterval,
        cmiFaRegVisitorTimeRemaining    TimeInterval,
        cmiFaRegVisitorRegFlags         RegistrationFlags,
        cmiFaRegVisitorRegIDLow         Unsigned32,
        cmiFaRegVisitorRegIDHigh        Unsigned32,
        cmiFaRegVisitorRegIsAccepted    TruthValue,
        cmiFaRegVisitorRegFlagsRev1     CmiRegistrationFlags,
        cmiFaRegVisitorChallengeValue   OCTET STRING
}

cmiFaRegVisitorIdentifierType OBJECT-TYPE
    SYNTAX          CmiEntityIdentifierType
    MAX-ACCESS      not-accessible
    STATUS          current
    DESCRIPTION
        "The type of the visitor's identifier."
    ::= { cmiFaRegVisitorEntry 1 }

cmiFaRegVisitorIdentifier OBJECT-TYPE
    SYNTAX          CmiEntityIdentifier
    MAX-ACCESS      not-accessible
    STATUS          current
    DESCRIPTION
        "The identifier associated with the visitor."
    ::= { cmiFaRegVisitorEntry 2 }

cmiFaRegVisitorHomeAddress OBJECT-TYPE
    SYNTAX          IpAddress
    MAX-ACCESS      read-only
    STATUS          current
    DESCRIPTION
        "Home (IP) address of visiting mobile node."
    ::= { cmiFaRegVisitorEntry 3 }

cmiFaRegVisitorHomeAgentAddress OBJECT-TYPE
    SYNTAX          IpAddress
    MAX-ACCESS      read-only
    STATUS          current
    DESCRIPTION
        "Home agent IP address for that visiting mobile node."
    ::= { cmiFaRegVisitorEntry 4 }

cmiFaRegVisitorTimeGranted OBJECT-TYPE
    SYNTAX          TimeInterval
    MAX-ACCESS      read-only
    STATUS          current
    DESCRIPTION
        "The lifetime granted to the mobile node for this
        registration.  Only valid if faVisitorRegIsAccepted
        is true(1)."
    ::= { cmiFaRegVisitorEntry 5 }

cmiFaRegVisitorTimeRemaining OBJECT-TYPE
    SYNTAX          TimeInterval
    MAX-ACCESS      read-only
    STATUS          current
    DESCRIPTION
        "The time remaining until the registration is expired.
        It has the same initial value as
        cmiFaRegVisitorTimeGranted, and is counted down by the
        foreign agent."
    ::= { cmiFaRegVisitorEntry 6 }

cmiFaRegVisitorRegFlags OBJECT-TYPE
    SYNTAX          RegistrationFlags
    MAX-ACCESS      read-only
    STATUS          deprecated
    DESCRIPTION
        "Registration flags sent by the mobile node."
    ::= { cmiFaRegVisitorEntry 7 }

cmiFaRegVisitorRegIDLow OBJECT-TYPE
    SYNTAX          Unsigned32 (0..4294967295)
    MAX-ACCESS      read-only
    STATUS          current
    DESCRIPTION
        "Low 32 bits of Identification used in that
        registration by the mobile node."
    ::= { cmiFaRegVisitorEntry 8 }

cmiFaRegVisitorRegIDHigh OBJECT-TYPE
    SYNTAX          Unsigned32 (0..4294967295)
    MAX-ACCESS      read-only
    STATUS          current
    DESCRIPTION
        "High 32 bits of Identification used in that
        registration by the mobile node."
    ::= { cmiFaRegVisitorEntry 9 }

cmiFaRegVisitorRegIsAccepted OBJECT-TYPE
    SYNTAX          TruthValue
    MAX-ACCESS      read-only
    STATUS          current
    DESCRIPTION
        "Whether the registration has been accepted or not. If
        it is false(2), this registration is still pending for
        reply."
    ::= { cmiFaRegVisitorEntry 10 }

cmiFaRegVisitorRegFlagsRev1 OBJECT-TYPE
    SYNTAX          CmiRegistrationFlags
    MAX-ACCESS      read-only
    STATUS          current
    DESCRIPTION
        "Registration flags sent by the mobile node."
    ::= { cmiFaRegVisitorEntry 11 }

cmiFaRegVisitorChallengeValue OBJECT-TYPE
    SYNTAX          OCTET STRING (SIZE  (256))
    MAX-ACCESS      read-only
    STATUS          current
    DESCRIPTION
        "Challenge value forwarded to MN in the previous
        Registration reply, which can be used by MN in the
        next Registration request"
    REFERENCE
        "RFC3012 - Mobile IPv4 Challenge/Response Extensions"
    ::= { cmiFaRegVisitorEntry 12 }



cmiFaInitRegRequestsReceived OBJECT-TYPE
    SYNTAX          Counter32
    MAX-ACCESS      read-only
    STATUS          current
    DESCRIPTION
        "Total number of initial Registration Requests received by
        the foreign agent."
    ::= { cmiFaReg 3 }

cmiFaInitRegRequestsRelayed OBJECT-TYPE
    SYNTAX          Counter32
    MAX-ACCESS      read-only
    STATUS          current
    DESCRIPTION
        "Total number of initial Registration Requests relayed by
        the foreign agent to the home agent."
    ::= { cmiFaReg 4 }

cmiFaInitRegRequestsDenied OBJECT-TYPE
    SYNTAX          Counter32
    MAX-ACCESS      read-only
    STATUS          current
    DESCRIPTION
        "Total number of initial Registration Requests denied by
        the foreign agent.

        The reasons for which FA denies a request include:

        1. FA CHAP authentication failures.

        2. HA is not reachable.

        3. No HA address set in the packet."
    ::= { cmiFaReg 5 }

cmiFaInitRegRequestsDiscarded OBJECT-TYPE
    SYNTAX          Counter32
    MAX-ACCESS      read-only
    STATUS          current
    DESCRIPTION
        "Total number of initial Registration Requests discarded
        by the foreign agent.

        The reasons for which FA discards a request include:

        1. ip mobile foreign-service is not enabled on the
        interface on which the request is received.

        2. NAI length exceeds the length of the packet.

        3. There are no active COAs."
    ::= { cmiFaReg 6 }

cmiFaInitRegRepliesValidFromHA OBJECT-TYPE
    SYNTAX          Counter32
    MAX-ACCESS      read-only
    STATUS          current
    DESCRIPTION
        "Total number of initial valid Registration Replies from
        the home agent to foreign agent."
    ::= { cmiFaReg 7 }

cmiFaInitRegRepliesValidRelayMN OBJECT-TYPE
    SYNTAX          Counter32
    MAX-ACCESS      read-only
    STATUS          current
    DESCRIPTION
        "Total number of initial Registration Replies relayed to
        MN by the foreign agent."
    ::= { cmiFaReg 8 }

cmiFaReRegRequestsReceived OBJECT-TYPE
    SYNTAX          Counter32
    MAX-ACCESS      read-only
    STATUS          current
    DESCRIPTION
        "Total number of Re-Registration Requests received by
        the foreign agent from mobile nodes."
    ::= { cmiFaReg 9 }

cmiFaReRegRequestsRelayed OBJECT-TYPE
    SYNTAX          Counter32
    MAX-ACCESS      read-only
    STATUS          current
    DESCRIPTION
        "Total number of Re-Registration Requests relayed to
        MN by the foreign agent."
    ::= { cmiFaReg 10 }

cmiFaReRegRequestsDenied OBJECT-TYPE
    SYNTAX          Counter32
    MAX-ACCESS      read-only
    STATUS          current
    DESCRIPTION
        "Total number of Re-Registration Requests denied by
        the foreign agent.

        Refer cmiFaInitRegRequestsDenied for the reasons for
        which FA denies a request."
    ::= { cmiFaReg 11 }

cmiFaReRegRequestsDiscarded OBJECT-TYPE
    SYNTAX          Counter32
    MAX-ACCESS      read-only
    STATUS          current
    DESCRIPTION
        "Total number of Re-Registration Requests discarded by
        the foreign agent.

        Refer cmiFaInitRegRequestsDiscarded for the reasons for
        which FA discards a request."
    ::= { cmiFaReg 12 }

cmiFaReRegRepliesValidFromHA OBJECT-TYPE
    SYNTAX          Counter32
    MAX-ACCESS      read-only
    STATUS          current
    DESCRIPTION
        "Total number of valid Re-Registration Replies from
        home agent."
    ::= { cmiFaReg 13 }

cmiFaReRegRepliesValidRelayToMN OBJECT-TYPE
    SYNTAX          Counter32
    MAX-ACCESS      read-only
    STATUS          current
    DESCRIPTION
        "Total number of valid Re-Registration Replies relayed
        to MN by the foreign agent."
    ::= { cmiFaReg 14 }

cmiFaDeRegRequestsReceived OBJECT-TYPE
    SYNTAX          Counter32
    MAX-ACCESS      read-only
    STATUS          current
    DESCRIPTION
        "Total number of De-Registration Requests received by
        the foreign agent."
    ::= { cmiFaReg 15 }

cmiFaDeRegRequestsRelayed OBJECT-TYPE
    SYNTAX          Counter32
    MAX-ACCESS      read-only
    STATUS          current
    DESCRIPTION
        "Total number of De-Registration Requests relayed to home
        agent by the foreign agent."
    ::= { cmiFaReg 16 }

cmiFaDeRegRequestsDenied OBJECT-TYPE
    SYNTAX          Counter32
    MAX-ACCESS      read-only
    STATUS          current
    DESCRIPTION
        "Total number of De-Registration Requests denied by the
        foreign agent.

        Refer cmiFaInitRegRequestsDenied for the reasons for
        which FA denies a request."
    ::= { cmiFaReg 17 }

cmiFaDeRegRequestsDiscarded OBJECT-TYPE
    SYNTAX          Counter32
    MAX-ACCESS      read-only
    STATUS          current
    DESCRIPTION
        "Total number of De-Registration Requests discarded by
        the foreign agent.

        Refer cmiFaInitRegRequestsDiscarded for the reasons for
        which FA discards a request."
    ::= { cmiFaReg 18 }

cmiFaDeRegRepliesValidFromHA OBJECT-TYPE
    SYNTAX          Counter32
    MAX-ACCESS      read-only
    STATUS          current
    DESCRIPTION
        "Total number of valid De-Registration Replies received
        from the home agent by the foreign agent."
    ::= { cmiFaReg 19 }

cmiFaDeRegRepliesValidRelayToMN OBJECT-TYPE
    SYNTAX          Counter32
    MAX-ACCESS      read-only
    STATUS          current
    DESCRIPTION
        "Total number of De-Registration Replies relayed to the
        MN by the foreign agent."
    ::= { cmiFaReg 20 }

cmiFaReverseTunnelUnavailable OBJECT-TYPE
    SYNTAX          Counter32
    MAX-ACCESS      read-only
    STATUS          current
    DESCRIPTION
        "Total number of Registration Requests denied by
        foreign agent -- requested reverse tunnel
        unavailable (Code 74)."
    REFERENCE       "RFC3024 - Reverse Tunneling for Mobile IP"
    ::= { cmiFaReg 21 }

cmiFaReverseTunnelBitNotSet OBJECT-TYPE
    SYNTAX          Counter32
    MAX-ACCESS      read-only
    STATUS          current
    DESCRIPTION
        "Total number of Registration Requests denied by
        foreign agent -- reverse tunnel is mandatory and
        'T' bit not set (Code 75)."
    REFERENCE       "RFC3024 - Reverse Tunneling for Mobile IP"
    ::= { cmiFaReg 22 }

cmiFaMnTooDistant OBJECT-TYPE
    SYNTAX          Counter32
    MAX-ACCESS      read-only
    STATUS          current
    DESCRIPTION
        "Total number of Registration Requests denied by
        foreign agent -- mobile node too distant (Code 76)."
    REFERENCE       "RFC3024 - Reverse Tunneling for Mobile IP"
    ::= { cmiFaReg 23 }

cmiFaDeliveryStyleUnsupported OBJECT-TYPE
    SYNTAX          Counter32
    MAX-ACCESS      read-only
    STATUS          current
    DESCRIPTION
        "Total number of Registration Requests denied by
        foreign agent -- delivery style not supported
        (Code 79)."
    REFERENCE       "RFC3024 - Reverse Tunneling for Mobile IP"
    ::= { cmiFaReg 24 }

cmiFaUnknownChallenge OBJECT-TYPE
    SYNTAX          Counter32
    MAX-ACCESS      read-only
    STATUS          current
    DESCRIPTION
        "Total number of Registration Requests denied by
        foreign agent -- challenge was unknown (code 104)."
    REFERENCE
        "RFC3012 - Mobile IPv4 Challenge/Response Extensions"
    ::= { cmiFaReg 25 }

cmiFaMissingChallenge OBJECT-TYPE
    SYNTAX          Counter32
    MAX-ACCESS      read-only
    STATUS          current
    DESCRIPTION
        "Total number of Registration Requests denied by
        foreign agent -- challenge was missing (code 105)."
    REFERENCE
        "RFC3012 - Mobile IPv4 Challenge/Response Extensions"
    ::= { cmiFaReg 26 }

cmiFaStaleChallenge OBJECT-TYPE
    SYNTAX          Counter32
    MAX-ACCESS      read-only
    STATUS          current
    DESCRIPTION
        "Total number of Registration Requests denied by
        foreign agent -- challenge was stale (code 106)."
    REFERENCE
        "RFC3012 - Mobile IPv4 Challenge/Response Extensions"
    ::= { cmiFaReg 27 }

cmiFaCvsesFromMnRejected OBJECT-TYPE
    SYNTAX          Counter32
    MAX-ACCESS      read-only
    STATUS          current
    DESCRIPTION
        "Total number of Registration Requests denied by
        foreign agent --  Unsupported Vendor-ID or unable to
        interpret Vendor-CVSE-Type in the CVSE sent by the
        mobile node to the foreign agent (code 100)."
    REFERENCE
        "RFC3025 - Mobile IP Vendor/Organization-Specific
        Extensions"
    ::= { cmiFaReg 28 }

cmiFaCvsesFromHaRejected OBJECT-TYPE
    SYNTAX          Counter32
    MAX-ACCESS      read-only
    STATUS          current
    DESCRIPTION
        "Total number of Registration Replies denied by
        foreign agent --  Unsupported Vendor-ID or unable to
        interpret Vendor-CVSE-Type in the CVSE sent by the
        home agent to the foreign agent (code 101)."
    REFERENCE
        "RFC3025 - Mobile IP Vendor/Organization-Specific
        Extensions"
    ::= { cmiFaReg 29 }

cmiFaNvsesFromMnNeglected OBJECT-TYPE
    SYNTAX          Counter32
    MAX-ACCESS      read-only
    STATUS          current
    DESCRIPTION
        "Total number of Registration Requests, which has
        an NVSE extension with - unsupported Vendor-ID or
        unable to interpret Vendor-NVSE-Type in the NVSE
        sent by the mobile node to the foreign agent."
    REFERENCE
        "RFC3025 - Mobile IP Vendor/Organization-Specific
        Extensions"
    ::= { cmiFaReg 30 }

cmiFaNvsesFromHaNeglected OBJECT-TYPE
    SYNTAX          Counter32
    MAX-ACCESS      read-only
    STATUS          current
    DESCRIPTION
        "Total number of Registration Requests, which has
        an NVSE extension with - unsupported Vendor-ID or
        unable to interpret Vendor-NVSE-Type in the NVSE
        sent by the home agent to the foreign agent."
    REFERENCE
        "RFC3025 - Mobile IP Vendor/Organization-Specific
        Extensions"
    ::= { cmiFaReg 31 }

cmiFaTotalRegRequests OBJECT-TYPE
    SYNTAX          Counter32
    MAX-ACCESS      read-only
    STATUS          current
    DESCRIPTION
        "Total number of Registration Requests received from the
        MN by the foreign agent."
    ::= { cmiFaReg 32 }

cmiFaTotalRegReplies OBJECT-TYPE
    SYNTAX          Counter32
    MAX-ACCESS      read-only
    STATUS          current
    DESCRIPTION
        "Total number of Registration Replies received from the
        MA by the foreign agent."
    ::= { cmiFaReg 33 }

cmiFaMnFaAuthFailures OBJECT-TYPE
    SYNTAX          Counter32
    MAX-ACCESS      read-only
    STATUS          current
    DESCRIPTION
        "Total number of Registration Requests denied due to
        MN and foreign agent auth extension failures."
    ::= { cmiFaReg 34 }

cmiFaMnAAAAuthFailures OBJECT-TYPE
    SYNTAX          Counter32
    MAX-ACCESS      read-only
    STATUS          current
    DESCRIPTION
        "Total number of Registration Requests denied due to
        MN-AAA auth extension failures."
    ::= { cmiFaReg 35 }
-- Foreign Agent Advertisement Group
-- FA needs to implement MA Advertisement Group plus that group
-- Foreign agent advertisement configuration table.

cmiFaAdvertConfTable OBJECT-TYPE
    SYNTAX          SEQUENCE OF CmiFaAdvertConfEntry
    MAX-ACCESS      not-accessible
    STATUS          current
    DESCRIPTION
        "A table containing additional configurable
        advertisement parameters beyond that provided by
        maAdvertConfTable for all advertisement interfaces
        in the foreign agent."
    ::= { cmiFaAdvertisement 1 }

cmiFaAdvertConfEntry OBJECT-TYPE
    SYNTAX          CmiFaAdvertConfEntry
    MAX-ACCESS      not-accessible
    STATUS          current
    DESCRIPTION
        "Additional advertisement parameters beyond that
        provided by maAdvertConfEntry for one advertisement
        interface."
    INDEX           { ifIndex }
    ::= { cmiFaAdvertConfTable 1 }

CmiFaAdvertConfEntry ::= SEQUENCE {
        cmiFaAdvertIsBusy          TruthValue,
        cmiFaAdvertRegRequired     TruthValue,
        cmiFaAdvertChallengeWindow Unsigned32
}

cmiFaAdvertIsBusy OBJECT-TYPE
    SYNTAX          TruthValue
    MAX-ACCESS      read-only
    STATUS          current
    DESCRIPTION
        "This object indicates if the foreign agent is busy.
        If the value of this object is true(1), agent
        advertisements sent by the agent on this interface
        will have the 'B' bit set to 1."
    ::= { cmiFaAdvertConfEntry 1 }

cmiFaAdvertRegRequired OBJECT-TYPE
    SYNTAX          TruthValue
    MAX-ACCESS      read-write
    STATUS          current
    DESCRIPTION
        "This object specifies if foreign agent registration
        is required on this interface. If the value of this
        object is true(1), agent advertisements sent on this
        interface will have the 'R' bit set to 1."
    DEFVAL          { false }
    ::= { cmiFaAdvertConfEntry 2 }

cmiFaAdvertChallengeWindow OBJECT-TYPE
    SYNTAX          Unsigned32 (1..10)
    MAX-ACCESS      read-write
    STATUS          current
    DESCRIPTION
        "Specifies the number of last challenge values
        which can be used by mobile node in the registration
        request sent to the foreign agent on this interface."
    REFERENCE
        "RFC3012 - Mobile IPv4 Challenge/Response Extensions"
    DEFVAL          { 2 }
    ::= { cmiFaAdvertConfEntry 3 }


-- Foreign Agent Advertisement Challenge Value Table

cmiFaAdvertChallengeTable OBJECT-TYPE
    SYNTAX          SEQUENCE OF CmiFaAdvertChallengeEntry
    MAX-ACCESS      not-accessible
    STATUS          current
    DESCRIPTION
        "A table containing challenge values in the challenge
        window. Foreign agent needs to implement maAdvertisement
        Group (MIP-MIB), that group's maAdvConfigTable and
        cmiFaAdvertChallengeWindow should be greater than 0."
    REFERENCE
        "RFC3012 - Mobile IPv4 Challenge/Response Extensions"
    ::= { cmiFaAdvertisement 2 }

cmiFaAdvertChallengeEntry OBJECT-TYPE
    SYNTAX          CmiFaAdvertChallengeEntry
    MAX-ACCESS      not-accessible
    STATUS          current
    DESCRIPTION
        "Challenge values in challenge window specific to an
        interface. This entry is created whenever the foreign
        agent sends an agent advertisement with challenge on
        the interface."
    INDEX           {
                        ifIndex,
                        cmiFaAdvertChallengeIndex
                    }
    ::= { cmiFaAdvertChallengeTable 1 }

CmiFaAdvertChallengeEntry ::= SEQUENCE {
        cmiFaAdvertChallengeIndex Unsigned32,
        cmiFaAdvertChallengeValue OCTET STRING
}

cmiFaAdvertChallengeIndex OBJECT-TYPE
    SYNTAX          Unsigned32 (1..10)
    MAX-ACCESS      not-accessible
    STATUS          current
    DESCRIPTION
        "The index of challenge table on an interface"
    ::= { cmiFaAdvertChallengeEntry 1 }

cmiFaAdvertChallengeValue OBJECT-TYPE
    SYNTAX          OCTET STRING (SIZE  (256))
    MAX-ACCESS      read-only
    STATUS          current
    DESCRIPTION
        "Challenge value in the challenge window of the
        interface."
    ::= { cmiFaAdvertChallengeEntry 2 }



-- Foreign Agent System Group

cmiFaRevTunnelSupported OBJECT-TYPE
    SYNTAX          TruthValue
    MAX-ACCESS      read-only
    STATUS          current
    DESCRIPTION
        "Indicates whether Reverse tunnel is supported or not."
    REFERENCE       "RFC3024 - Reverse Tunneling for Mobile IP"
    DEFVAL          { true }
    ::= { cmiFaSystem 1 }

cmiFaChallengeSupported OBJECT-TYPE
    SYNTAX          TruthValue
    MAX-ACCESS      read-only
    STATUS          current
    DESCRIPTION
        "Indicates whether Foreign Agent Challenge is supported
        or not."
    REFERENCE
        "RFC3012 - Mobile IPv4 Challenge/Response Extensions"
    DEFVAL          { true }
    ::= { cmiFaSystem 2 }

cmiFaEncapDeliveryStyleSupported OBJECT-TYPE
    SYNTAX          TruthValue
    MAX-ACCESS      read-only
    STATUS          current
    DESCRIPTION
        "Indicates whether Encap delivery style is supported or
        not."
    REFERENCE       "RFC3024 - Reverse Tunneling for Mobile IP"
    DEFVAL          { false }
    ::= { cmiFaSystem 3 }
-- Foreign Agent Interface Group

cmiFaInterfaceTable OBJECT-TYPE
    SYNTAX          SEQUENCE OF CmiFaInterfaceEntry
    MAX-ACCESS      not-accessible
    STATUS          current
    DESCRIPTION
        "A table containing interface specific parameters
        related to the foreign agent service on a FA."
    ::= { cmiFaSystem 4 }

cmiFaInterfaceEntry OBJECT-TYPE
    SYNTAX          CmiFaInterfaceEntry
    MAX-ACCESS      not-accessible
    STATUS          current
    DESCRIPTION
        "Parameters associated with a particular foreign agent
        interface. Interfaces on which foreign agent
        service has been enabled will have a corresponding
        entry."
    INDEX           { ifIndex }
    ::= { cmiFaInterfaceTable 1 }

CmiFaInterfaceEntry ::= SEQUENCE {
        cmiFaReverseTunnelEnable    TruthValue,
        cmiFaChallengeEnable        TruthValue,
        cmiFaAdvertChallengeChapSPI Unsigned32
}

cmiFaReverseTunnelEnable OBJECT-TYPE
    SYNTAX          TruthValue
    MAX-ACCESS      read-write
    STATUS          current
    DESCRIPTION
        "This object specifies whether reverse tunnel capability
        is enabled on the interface or not."
    DEFVAL          { false }
    ::= { cmiFaInterfaceEntry 1 }

cmiFaChallengeEnable OBJECT-TYPE
    SYNTAX          TruthValue
    MAX-ACCESS      read-write
    STATUS          current
    DESCRIPTION
        "This object specifies whether FA Challenge capability
        is enabled on the interface or not."
    REFERENCE
        "RFC3012 - Mobile IPv4 Challenge/Response Extensions"
    DEFVAL          { false }
    ::= { cmiFaInterfaceEntry 2 }

cmiFaAdvertChallengeChapSPI OBJECT-TYPE
    SYNTAX          Unsigned32 (1..4294967295)
    MAX-ACCESS      read-write
    STATUS          current
    DESCRIPTION
        "Specifies the CHAP_SPI number for FA challenge
        authentication."
    REFERENCE
        "RFC3012 - Mobile IPv4 Challenge/Response Extensions"
    DEFVAL          { 2 }
    ::= { cmiFaInterfaceEntry 3 }


-- Foreign Agent Asymmetric Link Support

cmiFaCoaTable OBJECT-TYPE
    SYNTAX          SEQUENCE OF CmiFaCoaEntry
    MAX-ACCESS      not-accessible
    STATUS          current
    DESCRIPTION
        "A table containing additional parameters for all
        care-of-addresses in the foreign agent beyond that
        provided by MIP MIB faCOATable."
    ::= { cmiFaSystem 5 }

cmiFaCoaEntry OBJECT-TYPE
    SYNTAX          CmiFaCoaEntry
    MAX-ACCESS      not-accessible
    STATUS          current
    DESCRIPTION
        "Additional information about a particular entry on
        the faCOATable beyond that provided by MIP MIB
        faCOAEntry."
    AUGMENTS           { faCOAEntry  }

    ::= { cmiFaCoaTable 1 }

CmiFaCoaEntry ::= SEQUENCE {
        cmiFaCoaInterfaceOnly TruthValue,
        cmiFaCoaTransmitOnly  TruthValue,
        cmiFaCoaRegAsymLink   ZeroBasedCounter32
}

cmiFaCoaInterfaceOnly OBJECT-TYPE
    SYNTAX          TruthValue
    MAX-ACCESS      read-create
    STATUS          current
    DESCRIPTION
        "Specifies whether the FA interface associated with
        this CoA should advertise only this CoA or not. If it
        is true, all the other configured care-of-addresses
        will not be advertised."
    DEFVAL          { false }
    ::= { cmiFaCoaEntry 1 }

cmiFaCoaTransmitOnly OBJECT-TYPE
    SYNTAX          TruthValue
    MAX-ACCESS      read-create
    STATUS          current
    DESCRIPTION
        "Specifies whether the FA interface associated with this
        CoA is a transmit-only (uplink) interface or not. If it
        is true, the FA treats all registration requests
        received (on any interface) for this CoA as having
        arrived on the care-of interface. This object can be set
        to true only for serial care-of-interfaces."
    DEFVAL          { false }
    ::= { cmiFaCoaEntry 2 }

cmiFaCoaRegAsymLink OBJECT-TYPE
    SYNTAX          ZeroBasedCounter32
    MAX-ACCESS      read-only
    STATUS          current
    DESCRIPTION
        "The number of registration requests which were
        received for this CoA on other interfaces (asymmetric
        links) and have been treated as received on this CoA
        interface. The count will thus be zero if the CoA
        interface is not set as transmit-only."
    ::= { cmiFaCoaEntry 3 }



-- Home Agent Registration Group

cmiHaRegTotalMobilityBindings OBJECT-TYPE
    SYNTAX          Gauge32
    MAX-ACCESS      read-only
    STATUS          current
    DESCRIPTION
        "The current number of entries in
        haMobilityBindingTable. haMobilityBindingTable
        contains the home agent's mobility binding list.
        The home agent updates this table in response to
        registration events from mobile nodes."
    REFERENCE       "RFC-2006 - Mobile IP MIB Definition using SMIv2"
    ::= { cmiHaReg 1 }

cmiHaRegMobilityBindingTable OBJECT-TYPE
    SYNTAX          SEQUENCE OF CmiHaRegMobilityBindingEntry
    MAX-ACCESS      not-accessible
    STATUS          current
    DESCRIPTION
        "The home agent updates this table in response to
        registration events from mobile nodes."
    ::= { cmiHaReg 2 }

cmiHaRegMobilityBindingEntry OBJECT-TYPE
    SYNTAX          CmiHaRegMobilityBindingEntry
    MAX-ACCESS      not-accessible
    STATUS          current
    DESCRIPTION
        "Additional information about a particular entry on
        the mobility binding list beyond that provided by
        MIP MIB haMobilityBindingEntry."
    AUGMENTS           { haMobilityBindingEntry  }

    ::= { cmiHaRegMobilityBindingTable 1 }

CmiHaRegMobilityBindingEntry ::= SEQUENCE {
        cmiHaRegMnIdentifierType          CmiEntityIdentifierType,
        cmiHaRegMnIdentifier              CmiEntityIdentifier,
        cmiHaRegMobilityBindingRegFlags   CmiRegistrationFlags,
        cmiHaRegMnIfDescription           SnmpAdminString,
        cmiHaRegMnIfBandwidth             Unsigned32,
        cmiHaRegMnIfID                    Unsigned32,
        cmiHaRegMnIfPathMetricType        CmiMultiPathMetricType,
        cmiHaRegMobilityBindingMacAddress MacAddress
}

cmiHaRegMnIdentifierType OBJECT-TYPE
    SYNTAX          CmiEntityIdentifierType
    MAX-ACCESS      read-only
    STATUS          current
    DESCRIPTION
        "The type of the mobile node's identifier."
    ::= { cmiHaRegMobilityBindingEntry 1 }

cmiHaRegMnIdentifier OBJECT-TYPE
    SYNTAX          CmiEntityIdentifier
    MAX-ACCESS      read-only
    STATUS          current
    DESCRIPTION
        "The identifier associated with the mobile node."
    ::= { cmiHaRegMobilityBindingEntry 2 }

cmiHaRegMobilityBindingRegFlags OBJECT-TYPE
    SYNTAX          CmiRegistrationFlags
    MAX-ACCESS      read-only
    STATUS          current
    DESCRIPTION
        "Registration flags sent by mobile node."
    ::= { cmiHaRegMobilityBindingEntry 3 }

cmiHaRegMnIfDescription OBJECT-TYPE
    SYNTAX          SnmpAdminString
    MAX-ACCESS      read-only
    STATUS          current
    DESCRIPTION
        "Description of the access type for the roaming
        interface of the registering mobile node or router."
    ::= { cmiHaRegMobilityBindingEntry 4 }

cmiHaRegMnIfBandwidth OBJECT-TYPE
    SYNTAX          Unsigned32
    UNITS           "kilobits/second"
    MAX-ACCESS      read-only
    STATUS          current
    DESCRIPTION
        "Bandwidth of the roaming interface through
        which mobile node or router is registered."
    ::= { cmiHaRegMobilityBindingEntry 5 }

cmiHaRegMnIfID OBJECT-TYPE
    SYNTAX          Unsigned32
    MAX-ACCESS      read-only
    STATUS          current
    DESCRIPTION
        "A unique number identifying the roaming interface
        through which mobile node or router is registered.
        This is also used as an unique identifier for the
        tunnel from home agent to the mobile router."
    ::= { cmiHaRegMobilityBindingEntry 6 }

cmiHaRegMnIfPathMetricType OBJECT-TYPE
    SYNTAX          CmiMultiPathMetricType
    MAX-ACCESS      read-only
    STATUS          current
    DESCRIPTION
        "Specifies the metric to use when multiple path
        is enabled."
    ::= { cmiHaRegMobilityBindingEntry 7 }

cmiHaRegMobilityBindingMacAddress OBJECT-TYPE
    SYNTAX          MacAddress
    MAX-ACCESS      read-only
    STATUS          current
    DESCRIPTION
        "This object represents the MAC address of Mobile Node."
    ::= { cmiHaRegMobilityBindingEntry 8 }


-- Home agent registration Counters per node

cmiHaRegCounterTable OBJECT-TYPE
    SYNTAX          SEQUENCE OF CmiHaRegCounterEntry
    MAX-ACCESS      not-accessible
    STATUS          current
    DESCRIPTION
        "A table containing registration statistics for all
        mobile nodes authorized to use this home agent. This
        table provides the same information as haCounterTable
        of MIP MIB. The only difference is that indices
        of table are changed so that mobile nodes which are
        not identified by the IP address will also be included
        in the table."
    ::= { cmiHaReg 3 }

cmiHaRegCounterEntry OBJECT-TYPE
    SYNTAX          CmiHaRegCounterEntry
    MAX-ACCESS      not-accessible
    STATUS          current
    DESCRIPTION
        "Registration statistics for a single mobile node."
    INDEX           {
                        cmiHaRegMnIdType,
                        cmiHaRegMnId
                    }
    ::= { cmiHaRegCounterTable 1 }

CmiHaRegCounterEntry ::= SEQUENCE {
        cmiHaRegMnIdType               CmiEntityIdentifierType,
        cmiHaRegMnId                   CmiEntityIdentifier,
        cmiHaRegServAcceptedRequests   Counter32,
        cmiHaRegServDeniedRequests     Counter32,
        cmiHaRegOverallServTime        TimeInterval,
        cmiHaRegRecentServAcceptedTime TimeStamp,
        cmiHaRegRecentServDeniedTime   TimeStamp,
        cmiHaRegRecentServDeniedCode   INTEGER
}

cmiHaRegMnIdType OBJECT-TYPE
    SYNTAX          CmiEntityIdentifierType
    MAX-ACCESS      not-accessible
    STATUS          current
    DESCRIPTION
        "The type of the mobile node's identifier."
    ::= { cmiHaRegCounterEntry 1 }

cmiHaRegMnId OBJECT-TYPE
    SYNTAX          CmiEntityIdentifier
    MAX-ACCESS      not-accessible
    STATUS          current
    DESCRIPTION
        "The identifier associated with the mobile node."
    ::= { cmiHaRegCounterEntry 2 }

cmiHaRegServAcceptedRequests OBJECT-TYPE
    SYNTAX          Counter32
    MAX-ACCESS      read-only
    STATUS          current
    DESCRIPTION
        "Total number of service requests for the mobile node
        accepted by the home agent (Code 0 + Code 1)."
    REFERENCE       "RFC-2002 - IP Mobility Support, section 3.4"
    ::= { cmiHaRegCounterEntry 3 }

cmiHaRegServDeniedRequests OBJECT-TYPE
    SYNTAX          Counter32
    MAX-ACCESS      read-only
    STATUS          current
    DESCRIPTION
        "Total number of service requests for the mobile node
        denied by the home agent (sum of all registrations
        denied with Code 128 through Code 159)."
    REFERENCE       "RFC-2002 - IP Mobility Support, section 3.4"
    ::= { cmiHaRegCounterEntry 4 }

cmiHaRegOverallServTime OBJECT-TYPE
    SYNTAX          TimeInterval
    MAX-ACCESS      read-only
    STATUS          current
    DESCRIPTION
        "Overall service time that has accumulated for the
        mobile node since the home agent last rebooted."
    ::= { cmiHaRegCounterEntry 5 }

cmiHaRegRecentServAcceptedTime OBJECT-TYPE
    SYNTAX          TimeStamp
    MAX-ACCESS      read-only
    STATUS          current
    DESCRIPTION
        "The time at which the most recent Registration
        Request was accepted by the home agent for this mobile
        node."
    REFERENCE       "RFC-2002 - IP Mobility Support, section 3"
    ::= { cmiHaRegCounterEntry 6 }

cmiHaRegRecentServDeniedTime OBJECT-TYPE
    SYNTAX          TimeStamp
    MAX-ACCESS      read-only
    STATUS          current
    DESCRIPTION
        "The time at which the most recent Registration
        Request was denied by the home agent for this mobile
        node."
    REFERENCE       "RFC-2002 - IP Mobility Support, section 3"
    ::= { cmiHaRegCounterEntry 7 }

cmiHaRegRecentServDeniedCode OBJECT-TYPE
    SYNTAX          INTEGER  {
                        reasonUnspecified(128),
                        admProhibited(129),
                        insufficientResource(130),
                        mnAuthenticationFailure(131),
                        faAuthenticationFailure(132),
                        idMismatch(133),
                        poorlyFormedRequest(134),
                        tooManyBindings(135),
                        unknownHA(136),
                        reverseTunnelUnavailable(137),
                        reverseTunnelBitNotSet(138),
                        encapsulationUnavailable(139)
                    }
    MAX-ACCESS      read-only
    STATUS          current
    DESCRIPTION
        "The Code indicating the reason why the most recent
        Registration Request for this mobile node was rejected
        by the home agent."
    REFERENCE       "RFC-2002 - IP Mobility Support, section 3.4"
    ::= { cmiHaRegCounterEntry 8 }



-- Home Agent registration processing Counters

cmiHaRegTotalProcLocRegs OBJECT-TYPE
    SYNTAX          Counter32
    MAX-ACCESS      read-only
    STATUS          current
    DESCRIPTION
        "The total number of Registration Requests processed
        by the home agent. It includes only those Registration
        Requests which were authenticated locally by the
        home agent."
    REFERENCE       "RFC-2002 - IP Mobility Support, section 3"
    ::= { cmiHaReg 4 }

cmiHaRegMaxProcLocInMinRegs OBJECT-TYPE
    SYNTAX          Counter32
    MAX-ACCESS      read-only
    STATUS          current
    DESCRIPTION
        "The maximum number of Registration Requests processed
        in a minute by the home agent. It includes only those
        Registration Requests which were authenticated locally
        by the home agent."
    REFERENCE       "RFC-2002 - IP Mobility Support, section 3"
    ::= { cmiHaReg 5 }

cmiHaRegDateMaxRegsProcLoc OBJECT-TYPE
    SYNTAX          DateAndTime
    MAX-ACCESS      read-only
    STATUS          current
    DESCRIPTION
        "The time at which number of Registration Requests
        processed in a minute by the home agent were maximum.
        It includes only those Registration Requests  which
        were authenticated locally by the home agent."
    REFERENCE       "RFC-2002 - IP Mobility Support, section 3"
    ::= { cmiHaReg 6 }

cmiHaRegProcLocInLastMinRegs OBJECT-TYPE
    SYNTAX          Counter32
    MAX-ACCESS      read-only
    STATUS          current
    DESCRIPTION
        "The number of Registration Requests processed in
        the last minute by the home agent. It includes only
        those Registration Requests which were authenticated
        locally by the home agent."
    REFERENCE       "RFC-2002 - IP Mobility Support, section 3"
    ::= { cmiHaReg 7 }

cmiHaRegTotalProcByAAARegs OBJECT-TYPE
    SYNTAX          Counter32
    MAX-ACCESS      read-only
    STATUS          current
    DESCRIPTION
        "The total number of Registration Requests processed
        by the home agent. It includes only those Registration
        Requests which were authenticated by the AAA server."
    REFERENCE       "RFC-2002 - IP Mobility Support, section 3"
    ::= { cmiHaReg 8 }

cmiHaRegMaxProcByAAAInMinRegs OBJECT-TYPE
    SYNTAX          Counter32
    MAX-ACCESS      read-only
    STATUS          current
    DESCRIPTION
        "The maximum number of Registration Requests processed
        in a minute by the home agent. It includes only those
        Registration Requests which were authenticated by the
        AAA server."
    REFERENCE       "RFC-2002 - IP Mobility Support, section 3"
    ::= { cmiHaReg 9 }

cmiHaRegDateMaxRegsProcByAAA OBJECT-TYPE
    SYNTAX          DateAndTime
    MAX-ACCESS      read-only
    STATUS          current
    DESCRIPTION
        "The time at which number of Registration Requests
        processed in a minute by the home agent were maximum.
        It includes only those Registration Requests which
        were authenticated by the AAA server."
    REFERENCE       "RFC-2002 - IP Mobility Support, section 3"
    ::= { cmiHaReg 10 }

cmiHaRegProcAAAInLastByMinRegs OBJECT-TYPE
    SYNTAX          Counter32
    MAX-ACCESS      read-only
    STATUS          current
    DESCRIPTION
        "The number of Registration Requests processed
        in the last minute by the home agent. It includes
        only those Registration Requests which were
        authenticated by the AAA server."
    REFERENCE       "RFC-2002 - IP Mobility Support, section 3"
    ::= { cmiHaReg 11 }

cmiHaRegAvgTimeRegsProcByAAA OBJECT-TYPE
    SYNTAX          Integer32 (0..2147483647)
    UNITS           "milli seconds"
    MAX-ACCESS      read-only
    STATUS          current
    DESCRIPTION
        "The average time taken by the home agent to process
        a Registration Request. It is calculated based on only
        those Registration Requests which were authenticated by
        the AAA server."
    REFERENCE       "RFC-2002 - IP Mobility Support, section 3"
    ::= { cmiHaReg 12 }

cmiHaRegMaxTimeRegsProcByAAA OBJECT-TYPE
    SYNTAX          Integer32 (0..2147483647)
    UNITS           "milli seconds"
    MAX-ACCESS      read-only
    STATUS          current
    DESCRIPTION
        "The maximum time taken by the home agent to process
        a Registration Request. It considers only those
        Registration Requests which were authenticated by
        the AAA server."
    REFERENCE       "RFC-2002 - IP Mobility Support, section 3"
    ::= { cmiHaReg 13 }

cmiHaRegRequestsReceived OBJECT-TYPE
    SYNTAX          Counter32
    MAX-ACCESS      read-only
    STATUS          current
    DESCRIPTION
        "Total number of Registration Requests received by the
        home agent.  This include initial registration requests,
        re-registration requests and de-registration requests."
    ::= { cmiHaReg 14 }

cmiHaRegRequestsDenied OBJECT-TYPE
    SYNTAX          Counter32
    MAX-ACCESS      read-only
    STATUS          current
    DESCRIPTION
        "Total number of Registration Requests denied by the home
        agent.

        The reasons for which HA denies a request include:

        1. Can't allocate IP address for MN.

        2. Request parsing failed.

        3. NAI length exceeds the packet length."
    ::= { cmiHaReg 15 }

cmiHaRegRequestsDiscarded OBJECT-TYPE
    SYNTAX          Counter32
    MAX-ACCESS      read-only
    STATUS          current
    DESCRIPTION
        "Total number of Registration Requests discarded by the
        home agent.

        The reasons for which HA discards a request include:

        1. ip mobile home-agent service is not enabled.

        2. HA-CHAP authentication failed.

        3. MN Security Association retrieval failed."
    ::= { cmiHaReg 16 }

cmiHaEncapUnavailable OBJECT-TYPE
    SYNTAX          Counter32
    MAX-ACCESS      read-only
    STATUS          current
    DESCRIPTION
        "Total number of Registration Requests denied by the home
        agent due to an unsupported encapsulation."
    ::= { cmiHaReg 17 }

cmiHaNAICheckFailures OBJECT-TYPE
    SYNTAX          Counter32
    MAX-ACCESS      read-only
    STATUS          current
    DESCRIPTION
        "Total number of Registration Requests denied by the home
        agent due to an NAI check failures."
    ::= { cmiHaReg 18 }

cmiHaInitRegRequestsReceived OBJECT-TYPE
    SYNTAX          Counter32
    MAX-ACCESS      read-only
    STATUS          current
    DESCRIPTION
        "Total number of initial Registration Requests received by
        the home agent."
    ::= { cmiHaReg 19 }

cmiHaInitRegRequestsAccepted OBJECT-TYPE
    SYNTAX          Counter32
    MAX-ACCESS      read-only
    STATUS          current
    DESCRIPTION
        "Total number of initial Registration Requests accepted by
        the home agent."
    ::= { cmiHaReg 20 }

cmiHaInitRegRequestsDenied OBJECT-TYPE
    SYNTAX          Counter32
    MAX-ACCESS      read-only
    STATUS          current
    DESCRIPTION
        "Total number of initial Registration Requests denied by
        the home agent.

        Refer cmiHaRegRequestsReceived for the reasons for which
        HA denies a request."
    ::= { cmiHaReg 21 }

cmiHaInitRegRequestsDiscarded OBJECT-TYPE
    SYNTAX          Counter32
    MAX-ACCESS      read-only
    STATUS          current
    DESCRIPTION
        "Total number of initial Registration Requests discarded
        by the home agent.

        Refer cmiHaRegRequestsDiscarded for the reasons for which
        HA discards a request."
    ::= { cmiHaReg 22 }

cmiHaReRegRequestsReceived OBJECT-TYPE
    SYNTAX          Counter32
    MAX-ACCESS      read-only
    STATUS          current
    DESCRIPTION
        "Total number of Re-Registration Requests received by the
        home agent."
    ::= { cmiHaReg 23 }

cmiHaReRegRequestsAccepted OBJECT-TYPE
    SYNTAX          Counter32
    MAX-ACCESS      read-only
    STATUS          current
    DESCRIPTION
        "Total number of Re-Registration Requests accepted by the
        home agent."
    ::= { cmiHaReg 24 }

cmiHaReRegRequestsDenied OBJECT-TYPE
    SYNTAX          Counter32
    MAX-ACCESS      read-only
    STATUS          current
    DESCRIPTION
        "Total number of Re-Registration Requests denied by the
        home agent.

        Refer cmiHaRegRequestsReceived for the reasons for which
        HA denies a request."
    ::= { cmiHaReg 25 }

cmiHaReRegRequestsDiscarded OBJECT-TYPE
    SYNTAX          Counter32
    MAX-ACCESS      read-only
    STATUS          current
    DESCRIPTION
        "Total number of Re-Registration Requests discarded by
        the home agent.

        Refer cmiHaRegRequestsDiscarded for the reasons for which
        HA discards a request."
    ::= { cmiHaReg 26 }

cmiHaDeRegRequestsReceived OBJECT-TYPE
    SYNTAX          Counter32
    MAX-ACCESS      read-only
    STATUS          current
    DESCRIPTION
        "Total number of De-Registration Requests received by
        the home agent."
    ::= { cmiHaReg 27 }

cmiHaDeRegRequestsAccepted OBJECT-TYPE
    SYNTAX          Counter32
    MAX-ACCESS      read-only
    STATUS          current
    DESCRIPTION
        "Total number of De-Registration Requests accepted by
        the home agent."
    ::= { cmiHaReg 28 }

cmiHaDeRegRequestsDenied OBJECT-TYPE
    SYNTAX          Counter32
    MAX-ACCESS      read-only
    STATUS          current
    DESCRIPTION
        "Total number of De-Registration Requests denied by the
        home agent.

        Refer cmiHaRegRequestsReceived for the reasons for which
        HA denies a request."
    ::= { cmiHaReg 29 }

cmiHaDeRegRequestsDiscarded OBJECT-TYPE
    SYNTAX          Counter32
    MAX-ACCESS      read-only
    STATUS          current
    DESCRIPTION
        "Total number of De-Registration Requests discarded by the
        home agent.

        Refer cmiHaRegRequestsDiscarded for the reasons for which
        HA discards a request."
    ::= { cmiHaReg 30 }

cmiHaReverseTunnelUnavailable OBJECT-TYPE
    SYNTAX          Counter32
    MAX-ACCESS      read-only
    STATUS          current
    DESCRIPTION
        "Total number of Registration Requests denied by
        the home agent -- requested reverse tunnel
        unavailable (Code 137)."
    REFERENCE       "RFC3024 - Reverse Tunneling for Mobile IP"
    ::= { cmiHaReg 31 }

cmiHaReverseTunnelBitNotSet OBJECT-TYPE
    SYNTAX          Counter32
    MAX-ACCESS      read-only
    STATUS          current
    DESCRIPTION
        "Total number of Registration Requests denied by
        the home agent -- reverse tunnel is mandatory and
        'T' bit not set (Code 138)."
    REFERENCE       "RFC3024 - Reverse Tunneling for Mobile IP"
    ::= { cmiHaReg 32 }

cmiHaEncapsulationUnavailable OBJECT-TYPE
    SYNTAX          Counter32
    MAX-ACCESS      read-only
    STATUS          current
    DESCRIPTION
        "Total number of Registration Requests denied by
        the home agent -- requested encapsulation
        unavailable (Code 72)."
    REFERENCE       "RFC3024 - Reverse Tunneling for Mobile IP"
    ::= { cmiHaReg 33 }

cmiHaCvsesFromMnRejected OBJECT-TYPE
    SYNTAX          Counter32
    MAX-ACCESS      read-only
    STATUS          current
    DESCRIPTION
        "Total number of Registration Requests denied by the
        home agent --  Unsupported Vendor-ID or unable to
        interpret Vendor-CVSE-Type in the CVSE sent by the
        mobile node to the home agent (code 140)."
    REFERENCE
        "RFC3025 - Mobile IP Vendor/Organization-Specific
        Extensions"
    ::= { cmiHaReg 34 }

cmiHaCvsesFromFaRejected OBJECT-TYPE
    SYNTAX          Counter32
    MAX-ACCESS      read-only
    STATUS          current
    DESCRIPTION
        "Total number of Registration Requests denied by the
        home agent --  Unsupported Vendor-ID or unable to
        interpret Vendor-CVSE-Type in the CVSE sent by the
        foreign agent to the home agent (code 141)."
    REFERENCE
        "RFC3025 - Mobile IP Vendor/Organization-Specific
        Extensions"
    ::= { cmiHaReg 35 }

cmiHaNvsesFromMnNeglected OBJECT-TYPE
    SYNTAX          Counter32
    MAX-ACCESS      read-only
    STATUS          current
    DESCRIPTION
        "Total number of Registration Requests, which has
        an NVSE extension with - unsupported Vendor-ID or
        unable to interpret Vendor-NVSE-Type in the NVSE
        sent by the mobile node to the home agent."
    REFERENCE
        "RFC3025 - Mobile IP Vendor/Organization-Specific
        Extensions"
    ::= { cmiHaReg 36 }

cmiHaNvsesFromFaNeglected OBJECT-TYPE
    SYNTAX          Counter32
    MAX-ACCESS      read-only
    STATUS          current
    DESCRIPTION
        "Total number of Registration Requests, which has
        an NVSE extension with - unsupported Vendor-ID or
        unable to interpret Vendor-NVSE-Type in the NVSE
        sent by the foreign agent to the home agent."
    REFERENCE
        "RFC3025 - Mobile IP Vendor/Organization-Specific
        Extensions"
    ::= { cmiHaReg 37 }

cmiHaMnHaAuthFailures OBJECT-TYPE
    SYNTAX          Counter32
    MAX-ACCESS      read-only
    STATUS          current
    DESCRIPTION
        "Total number of Registration Requests denied due to
        MN and home agent auth extension failures."
    ::= { cmiHaReg 38 }

cmiHaMnAAAAuthFailures OBJECT-TYPE
    SYNTAX          Counter32
    MAX-ACCESS      read-only
    STATUS          current
    DESCRIPTION
        "Total number of Registration Requests denied due to
        MN-AAA auth extension failures."
    ::= { cmiHaReg 39 }

cmiHaMaximumBindings OBJECT-TYPE
    SYNTAX          Unsigned32 (1..500000)
    MAX-ACCESS      read-write
    STATUS          current
    DESCRIPTION
        "This object represents the maximum number of
        registrations allowed by the home agent."
    DEFVAL          { 235000 }
    ::= { cmiHaReg 40 }

cmiHaRegIntervalSize OBJECT-TYPE
    SYNTAX          Unsigned32 (15..300)
    UNITS           "minutes"
    MAX-ACCESS      read-write
    STATUS          current
    DESCRIPTION
        "This object represents the interval for which
        cmiHaRegIntervalMaxActiveBindings,
        cmiHaRegInterval3gpp2MaxActiveBindings,
        cmiHaRegIntervalWimaxMaxActiveBindings are calculated."
    DEFVAL          { 30 }
    ::= { cmiHaReg 41 }

cmiHaRegIntervalMaxActiveBindings OBJECT-TYPE
    SYNTAX          Gauge32
    UNITS           "MIP call per interval"
    MAX-ACCESS      read-only
    STATUS          current
    DESCRIPTION
        "This object represents the maximum number of active bindings
        present at any time during the elapsed time interval configured
        through cmiHaRegIntervalSize. When the time interval is modified
        through cmiHaRegIntervalSize, a value of zero will be populated
        till one complete new interval is elapsed."
    ::= { cmiHaReg 42 }

cmiHaRegInterval3gpp2MaxActiveBindings OBJECT-TYPE
    SYNTAX          Gauge32
    UNITS           "MIP call per interval"
    MAX-ACCESS      read-only
    STATUS          current
    DESCRIPTION
        "This object represents the maximum number of active 3GPP2
        bindings present at any time during the elapsed time interval
        configured through cmiHaRegIntervalSize. When the time interval
        is modified through cmiHaRegIntervalSize, a value of zero will
        be populated till one complete new interval is elapsed."
    ::= { cmiHaReg 43 }

cmiHaRegIntervalWimaxMaxActiveBindings OBJECT-TYPE
    SYNTAX          Gauge32
    UNITS           "MIP call per interval"
    MAX-ACCESS      read-only
    STATUS          current
    DESCRIPTION
        "This object represents the maximum number of active WIMAX
        bindings present at any time during the elapsed time interval
        configured through cmiHaRegIntervalSize. When the time interval
        is modified through cmiHaRegIntervalSize, a value of zero will
        be populated till one complete new interval is elapsed."
    ::= { cmiHaReg 44 }

cmiHaRegTunnelStatsTable OBJECT-TYPE
    SYNTAX          SEQUENCE OF CmiHaRegTunnelStatsEntry
    MAX-ACCESS      not-accessible
    STATUS          current
    DESCRIPTION
        "This table provides the statistics about the active tunnels
        between HA and CoA.

        A row is added to this table when a new tunnel is created
        between HA and CoA. A row is deleted in this table when an
        existing tunnel between HA and CoA is deleted."
    ::= { cmiHaReg 45 }

cmiHaRegTunnelStatsEntry OBJECT-TYPE
    SYNTAX          CmiHaRegTunnelStatsEntry
    MAX-ACCESS      not-accessible
    STATUS          current
    DESCRIPTION
        "Each entry represents a conceptual row in
        cmiHaRegTunnelStatsTable and corresponds to the statistics for
        a single active tunnel between HA and CoA."
    INDEX           {
                        cmiHaRegTunnelStatsSrcAddrType,
                        cmiHaRegTunnelStatsSrcAddr,
                        cmiHaRegTunnelStatsDestAddrType,
                        cmiHaRegTunnelStatsDestAddr
                    }
    ::= { cmiHaRegTunnelStatsTable 1 }

CmiHaRegTunnelStatsEntry ::= SEQUENCE {
        cmiHaRegTunnelStatsSrcAddrType  InetAddressType,
        cmiHaRegTunnelStatsSrcAddr      InetAddress,
        cmiHaRegTunnelStatsDestAddrType InetAddressType,
        cmiHaRegTunnelStatsDestAddr     InetAddress,
        cmiHaRegTunnelStatsTunnelType   CmiTunnelType,
        cmiHaRegTunnelStatsNumUsers     Gauge32,
        cmiHaRegTunnelStatsDataRateInt  Unsigned32,
        cmiHaRegTunnelStatsInBitRate    CounterBasedGauge64,
        cmiHaRegTunnelStatsInPktRate    CounterBasedGauge64,
        cmiHaRegTunnelStatsInBytes      Counter64,
        cmiHaRegTunnelStatsInPkts       Counter64,
        cmiHaRegTunnelStatsOutBitRate   CounterBasedGauge64,
        cmiHaRegTunnelStatsOutPktRate   CounterBasedGauge64,
        cmiHaRegTunnelStatsOutBytes     Counter64,
        cmiHaRegTunnelStatsOutPkts      Counter64
}

cmiHaRegTunnelStatsSrcAddrType OBJECT-TYPE
    SYNTAX          InetAddressType
    MAX-ACCESS      not-accessible
    STATUS          current
    DESCRIPTION
        "This object represents the type of the address stored in
        cmiHaRegTunnelStatsSrcAddr."
    ::= { cmiHaRegTunnelStatsEntry 1 }

cmiHaRegTunnelStatsSrcAddr OBJECT-TYPE
    SYNTAX          InetAddress
    MAX-ACCESS      not-accessible
    STATUS          current
    DESCRIPTION
        "This object represents the source address of the tunnel."
    ::= { cmiHaRegTunnelStatsEntry 2 }

cmiHaRegTunnelStatsDestAddrType OBJECT-TYPE
    SYNTAX          InetAddressType
    MAX-ACCESS      not-accessible
    STATUS          current
    DESCRIPTION
        "This object represents the type of the address stored in
        cmiHaRegTunnelStatsDestAddr."
    ::= { cmiHaRegTunnelStatsEntry 3 }

cmiHaRegTunnelStatsDestAddr OBJECT-TYPE
    SYNTAX          InetAddress
    MAX-ACCESS      not-accessible
    STATUS          current
    DESCRIPTION
        "This object represents the destination address of the tunnel."
    ::= { cmiHaRegTunnelStatsEntry 4 }

cmiHaRegTunnelStatsTunnelType OBJECT-TYPE
    SYNTAX          CmiTunnelType
    MAX-ACCESS      read-only
    STATUS          current
    DESCRIPTION
        "This object represents the tunneling protocol in use between
        the HA and CoA."
    ::= { cmiHaRegTunnelStatsEntry 5 }

cmiHaRegTunnelStatsNumUsers OBJECT-TYPE
    SYNTAX          Gauge32
    MAX-ACCESS      read-only
    STATUS          current
    DESCRIPTION
        "This object represents the number of users on the tunnel."
    ::= { cmiHaRegTunnelStatsEntry 6 }

cmiHaRegTunnelStatsDataRateInt OBJECT-TYPE
    SYNTAX          Unsigned32
    UNITS           "seconds"
    MAX-ACCESS      read-only
    STATUS          current
    DESCRIPTION
        "This object represents the interval for which
        cmiHaRegTunnelStatsInBitRate, cmiHaRegTunnelStatsInPktRate,
        cmiHaRegTunnelStatsOutBitRate and cmiHaRegTunnelStatsOutPktRate
        are calculated."
    ::= { cmiHaRegTunnelStatsEntry 7 }

cmiHaRegTunnelStatsInBitRate OBJECT-TYPE
    SYNTAX          CounterBasedGauge64
    UNITS           "bits per second"
    MAX-ACCESS      read-only
    STATUS          current
    DESCRIPTION
        "This object represents the number of bits received at the
        tunnel per second in the interval represented by
        cmiHaRegTunnelStatsDataRateInt."
    ::= { cmiHaRegTunnelStatsEntry 8 }

cmiHaRegTunnelStatsInPktRate OBJECT-TYPE
    SYNTAX          CounterBasedGauge64
    UNITS           "packets per second"
    MAX-ACCESS      read-only
    STATUS          current
    DESCRIPTION
        "This object represents the number of packets received at the
        tunnel  per second in the interval represented by
        cmiHaRegTunnelStatsDataRateInt."
    ::= { cmiHaRegTunnelStatsEntry 9 }

cmiHaRegTunnelStatsInBytes OBJECT-TYPE
    SYNTAX          Counter64
    MAX-ACCESS      read-only
    STATUS          current
    DESCRIPTION
        "This object represents the total number of bytes received at
        the tunnel."
    ::= { cmiHaRegTunnelStatsEntry 10 }

cmiHaRegTunnelStatsInPkts OBJECT-TYPE
    SYNTAX          Counter64
    MAX-ACCESS      read-only
    STATUS          current
    DESCRIPTION
        "This object represents the total number of packets received at
        the tunnel."
    ::= { cmiHaRegTunnelStatsEntry 11 }

cmiHaRegTunnelStatsOutBitRate OBJECT-TYPE
    SYNTAX          CounterBasedGauge64
    UNITS           "bits per second"
    MAX-ACCESS      read-only
    STATUS          current
    DESCRIPTION
        "This object represents the number of bits transmitted from the
        tunnel per second in the interval represented by
        cmiHaRegTunnelStatsDataRateInt."
    ::= { cmiHaRegTunnelStatsEntry 12 }

cmiHaRegTunnelStatsOutPktRate OBJECT-TYPE
    SYNTAX          CounterBasedGauge64
    UNITS           "packets per second"
    MAX-ACCESS      read-only
    STATUS          current
    DESCRIPTION
        "This object represents the number of packets transmitted from
        the tunnel per second in the interval represented by
        cmiHaRegTunnelStatsDataRateInt."
    ::= { cmiHaRegTunnelStatsEntry 13 }

cmiHaRegTunnelStatsOutBytes OBJECT-TYPE
    SYNTAX          Counter64
    MAX-ACCESS      read-only
    STATUS          current
    DESCRIPTION
        "This object represents the total number of bytes transmitted
        from the tunnel."
    ::= { cmiHaRegTunnelStatsEntry 14 }

cmiHaRegTunnelStatsOutPkts OBJECT-TYPE
    SYNTAX          Counter64
    MAX-ACCESS      read-only
    STATUS          current
    DESCRIPTION
        "This object represents the total number of packets transmitted
        from the tunnel."
    ::= { cmiHaRegTunnelStatsEntry 15 }



-- Home Agent Redundancy Group

cmiHaRedunSentBUs OBJECT-TYPE
    SYNTAX          Counter32
    MAX-ACCESS      read-only
    STATUS          current
    DESCRIPTION
        "Total number of binding updates sent by the home
        agent."
    ::= { cmiHaRedun 1 }

cmiHaRedunFailedBUs OBJECT-TYPE
    SYNTAX          Counter32
    MAX-ACCESS      read-only
    STATUS          current
    DESCRIPTION
        "Total number of binding updates sent by the home
        agent for which no acknowledgement is received
        from the standby home agent."
    ::= { cmiHaRedun 2 }

cmiHaRedunReceivedBUAcks OBJECT-TYPE
    SYNTAX          Counter32
    MAX-ACCESS      read-only
    STATUS          current
    DESCRIPTION
        "Total number of acknowledgements received in response
        to binding updates sent by the home agent."
    ::= { cmiHaRedun 3 }

cmiHaRedunTotalSentBUs OBJECT-TYPE
    SYNTAX          Counter32
    MAX-ACCESS      read-only
    STATUS          current
    DESCRIPTION
        "Total number of binding updates sent by the home
        agent including retransmissions of same binding
        update."
    ::= { cmiHaRedun 4 }

cmiHaRedunReceivedBUs OBJECT-TYPE
    SYNTAX          Counter32
    MAX-ACCESS      read-only
    STATUS          current
    DESCRIPTION
        "Total number of binding updates received by the
        home agent."
    ::= { cmiHaRedun 5 }

cmiHaRedunSentBUAcks OBJECT-TYPE
    SYNTAX          Counter32
    MAX-ACCESS      read-only
    STATUS          current
    DESCRIPTION
        "Total number of acknowledgements sent in response to
        binding updates received by the home agent."
    ::= { cmiHaRedun 6 }

cmiHaRedunSentBIReqs OBJECT-TYPE
    SYNTAX          Counter32
    MAX-ACCESS      read-only
    STATUS          current
    DESCRIPTION
        "Total number of binding information requests sent
        by the home agent."
    ::= { cmiHaRedun 7 }

cmiHaRedunFailedBIReqs OBJECT-TYPE
    SYNTAX          Counter32
    MAX-ACCESS      read-only
    STATUS          current
    DESCRIPTION
        "Total number of binding information requests sent
        by the home agent for which no reply is received from
        the active home agent."
    ::= { cmiHaRedun 8 }

cmiHaRedunTotalSentBIReqs OBJECT-TYPE
    SYNTAX          Counter32
    MAX-ACCESS      read-only
    STATUS          current
    DESCRIPTION
        "Total number of binding information requests sent
        by the home agent including retransmissions of the
        same request."
    ::= { cmiHaRedun 9 }

cmiHaRedunReceivedBIReps OBJECT-TYPE
    SYNTAX          Counter32
    MAX-ACCESS      read-only
    STATUS          current
    DESCRIPTION
        "Total number of binding information replies received
        by the home agent."
    ::= { cmiHaRedun 10 }

cmiHaRedunDroppedBIReps OBJECT-TYPE
    SYNTAX          Counter32
    MAX-ACCESS      read-only
    STATUS          current
    DESCRIPTION
        "Total number of binding information replies dropped
        since there is no corresponding binding information
        request sent by the home agent."
    ::= { cmiHaRedun 11 }

cmiHaRedunSentBIAcks OBJECT-TYPE
    SYNTAX          Counter32
    MAX-ACCESS      read-only
    STATUS          current
    DESCRIPTION
        "Total number of acknowledgements sent in response to
        binding information replies received by the home
        agent."
    ::= { cmiHaRedun 12 }

cmiHaRedunReceivedBIReqs OBJECT-TYPE
    SYNTAX          Counter32
    MAX-ACCESS      read-only
    STATUS          current
    DESCRIPTION
        "Total number of binding information requests received
        by the home agent."
    ::= { cmiHaRedun 13 }

cmiHaRedunSentBIReps OBJECT-TYPE
    SYNTAX          Counter32
    MAX-ACCESS      read-only
    STATUS          current
    DESCRIPTION
        "Total number of binding information replies sent by
        the home agent."
    ::= { cmiHaRedun 14 }

cmiHaRedunFailedBIReps OBJECT-TYPE
    SYNTAX          Counter32
    MAX-ACCESS      read-only
    STATUS          current
    DESCRIPTION
        "Total number of binding information replies sent by
        by the home agent for which no acknowledgement is
        received from the standby home agent."
    ::= { cmiHaRedun 15 }

cmiHaRedunTotalSentBIReps OBJECT-TYPE
    SYNTAX          Counter32
    MAX-ACCESS      read-only
    STATUS          current
    DESCRIPTION
        "Total number of binding information replies sent
        by the home agent including retransmissions of the
        same reply."
    ::= { cmiHaRedun 16 }

cmiHaRedunReceivedBIAcks OBJECT-TYPE
    SYNTAX          Counter32
    MAX-ACCESS      read-only
    STATUS          current
    DESCRIPTION
        "Total number of acknowledgements received in response
        to binding information replies sent by the home
        agent."
    ::= { cmiHaRedun 17 }

cmiHaRedunDroppedBIAcks OBJECT-TYPE
    SYNTAX          Counter32
    MAX-ACCESS      read-only
    STATUS          current
    DESCRIPTION
        "Total number of acknowledgements dropped by the
        home agent since there are no corresponding binding
        information replies sent by it."
    ::= { cmiHaRedun 18 }

cmiHaRedunSecViolations OBJECT-TYPE
    SYNTAX          Counter32
    MAX-ACCESS      read-only
    STATUS          current
    DESCRIPTION
        "Total number of security violations in the home
        agent caused by processing of the packets received
        from the peer home agent. Security violations can
        occur due to the following reasons.
        - the authenticator value in the packet is invalid.
        - value stored in the identification field of the
          packet is invalid."
    ::= { cmiHaRedun 19 }
-- Home Agent mobile network group

cmiHaMrTable OBJECT-TYPE
    SYNTAX          SEQUENCE OF CmiHaMrEntry
    MAX-ACCESS      not-accessible
    STATUS          current
    DESCRIPTION
        "A table containing details about all mobile routers
        associated with the Home Agent."
    ::= { cmiHaMobNet 1 }

cmiHaMrEntry OBJECT-TYPE
    SYNTAX          CmiHaMrEntry
    MAX-ACCESS      not-accessible
    STATUS          current
    DESCRIPTION
        "Information related to a single mobile router
        associated with the Home Agent."
    INDEX           {
                        cmiHaMrAddrType,
                        cmiHaMrAddr
                    }
    ::= { cmiHaMrTable 1 }

CmiHaMrEntry ::= SEQUENCE {
        cmiHaMrAddrType            InetAddressType,
        cmiHaMrAddr                InetAddress,
        cmiHaMrDynamic             TruthValue,
        cmiHaMrStatus              RowStatus,
        cmiHaMrMultiPath           TruthValue,
        cmiHaMrMultiPathMetricType CmiMultiPathMetricType
}

cmiHaMrAddrType OBJECT-TYPE
    SYNTAX          InetAddressType
    MAX-ACCESS      not-accessible
    STATUS          current
    DESCRIPTION
        "Represents the type of IP address stored in
        cmiHaMrAddr. Only IPv4 address type is supported."
    ::= { cmiHaMrEntry 1 }

cmiHaMrAddr OBJECT-TYPE
    SYNTAX          InetAddress (SIZE  (4 | 16))
    MAX-ACCESS      not-accessible
    STATUS          current
    DESCRIPTION
        "IP address of a mobile router providing mobility
        to one or more networks. Only IPv4 addresses are
        supported."
    ::= { cmiHaMrEntry 2 }

cmiHaMrDynamic OBJECT-TYPE
    SYNTAX          TruthValue
    MAX-ACCESS      read-create
    STATUS          current
    DESCRIPTION
        "Specifies whether the mobile router is capable of
        registering networks dynamically or not."
    DEFVAL          { false }
    ::= { cmiHaMrEntry 3 }

cmiHaMrStatus OBJECT-TYPE
    SYNTAX          RowStatus
    MAX-ACCESS      read-create
    STATUS          current
    DESCRIPTION
        "The row status for the MR entry."
    ::= { cmiHaMrEntry 4 }

cmiHaMrMultiPath OBJECT-TYPE
    SYNTAX          TruthValue
    MAX-ACCESS      read-create
    STATUS          current
    DESCRIPTION
        "Specifies whether multiple path is enabled
        on this mobile router or not."
    DEFVAL          { false }
    ::= { cmiHaMrEntry 5 }

cmiHaMrMultiPathMetricType OBJECT-TYPE
    SYNTAX          CmiMultiPathMetricType
    MAX-ACCESS      read-create
    STATUS          current
    DESCRIPTION
        "Specifies the metric to use when multiple path
        is enabled."
    DEFVAL          { bandwidth }
    ::= { cmiHaMrEntry 6 }



cmiHaMobNetTable OBJECT-TYPE
    SYNTAX          SEQUENCE OF CmiHaMobNetEntry
    MAX-ACCESS      not-accessible
    STATUS          current
    DESCRIPTION
        "A table containing information about all the mobile
        networks associated with a Home Agent."
    ::= { cmiHaMobNet 2 }

cmiHaMobNetEntry OBJECT-TYPE
    SYNTAX          CmiHaMobNetEntry
    MAX-ACCESS      not-accessible
    STATUS          current
    DESCRIPTION
        "Information of a single mobile network associated with
        a Home Agent."
    INDEX           {
                        cmiHaMrAddrType,
                        cmiHaMrAddr,
                        cmiHaMobNetAddressType,
                        cmiHaMobNetAddress,
                        cmiHaMobNetPfxLen
                    }
    ::= { cmiHaMobNetTable 1 }

CmiHaMobNetEntry ::= SEQUENCE {
        cmiHaMobNetAddressType InetAddressType,
        cmiHaMobNetAddress     InetAddress,
        cmiHaMobNetPfxLen      InetAddressPrefixLength,
        cmiHaMobNetDynamic     TruthValue,
        cmiHaMobNetStatus      RowStatus
}

cmiHaMobNetAddressType OBJECT-TYPE
    SYNTAX          InetAddressType
    MAX-ACCESS      not-accessible
    STATUS          current
    DESCRIPTION
        "Represents the type of IP address stored in
        cmiHaMobNetAddress. Only IPv4 address type is
        supported."
    ::= { cmiHaMobNetEntry 1 }

cmiHaMobNetAddress OBJECT-TYPE
    SYNTAX          InetAddress (SIZE  (4 | 16))
    MAX-ACCESS      not-accessible
    STATUS          current
    DESCRIPTION
        "IP address of the mobile network. Only IPv4 addresses
        are supported."
    ::= { cmiHaMobNetEntry 2 }

cmiHaMobNetPfxLen OBJECT-TYPE
    SYNTAX          InetAddressPrefixLength
    MAX-ACCESS      not-accessible
    STATUS          current
    DESCRIPTION
        "Prefix length associated with the mobile network
        ip address."
    ::= { cmiHaMobNetEntry 3 }

cmiHaMobNetDynamic OBJECT-TYPE
    SYNTAX          TruthValue
    MAX-ACCESS      read-only
    STATUS          current
    DESCRIPTION
        "Indicates whether the mobile network has been
        registered dynamically or not."
    ::= { cmiHaMobNetEntry 4 }

cmiHaMobNetStatus OBJECT-TYPE
    SYNTAX          RowStatus
    MAX-ACCESS      read-create
    STATUS          current
    DESCRIPTION
        "The row status for the mobile network entry."
    ::= { cmiHaMobNetEntry 5 }



-- cmiSecurity Group

cmiSecAssocsCount OBJECT-TYPE
    SYNTAX          Gauge32
    MAX-ACCESS      read-only
    STATUS          current
    DESCRIPTION
        "Total number of mobility security associations
        known to the entity i.e. the number of entries in
        the cmiSecAssocTable."
    ::= { cmiSecurity 1 }

cmiSecAssocTable OBJECT-TYPE
    SYNTAX          SEQUENCE OF CmiSecAssocEntry
    MAX-ACCESS      not-accessible
    STATUS          current
    DESCRIPTION
        "A table containing Mobility Security Associations.
        This table provides the same information as
        mipSecAssocTable of MIP MIB. The differences are:
        - indices of the table are changed so that mobile
          nodes which are not identified by the IP address will
          also be included in the table.
        - rowStatus object is added to the table."
    ::= { cmiSecurity 2 }

cmiSecAssocEntry OBJECT-TYPE
    SYNTAX          CmiSecAssocEntry
    MAX-ACCESS      not-accessible
    STATUS          current
    DESCRIPTION
        "One particular Mobility Security Association."
    INDEX           {
                        cmiSecPeerIdentifierType,
                        cmiSecPeerIdentifier,
                        cmiSecSPI
                    }
    ::= { cmiSecAssocTable 1 }

CmiSecAssocEntry ::= SEQUENCE {
        cmiSecPeerIdentifierType CmiEntityIdentifierType,
        cmiSecPeerIdentifier     CmiEntityIdentifier,
        cmiSecSPI                CmiSpi,
        cmiSecAlgorithmType      INTEGER,
        cmiSecAlgorithmMode      INTEGER,
        cmiSecKey                OCTET STRING,
        cmiSecReplayMethod       INTEGER,
        cmiSecStatus             RowStatus,
        cmiSecKey2               OCTET STRING
}

cmiSecPeerIdentifierType OBJECT-TYPE
    SYNTAX          CmiEntityIdentifierType
    MAX-ACCESS      not-accessible
    STATUS          current
    DESCRIPTION
        "The type of the peer entity's identifier."
    ::= { cmiSecAssocEntry 1 }

cmiSecPeerIdentifier OBJECT-TYPE
    SYNTAX          CmiEntityIdentifier
    MAX-ACCESS      not-accessible
    STATUS          current
    DESCRIPTION
        "The identifier of the peer entity with which this
        node shares the mobility security association."
    ::= { cmiSecAssocEntry 2 }

cmiSecSPI OBJECT-TYPE
    SYNTAX          CmiSpi
    MAX-ACCESS      not-accessible
    STATUS          current
    DESCRIPTION
        "The SPI is the 4-byte index within the Mobility
        Security Association which selects the specific
        security parameters to be used to authenticate the
        peer, i.e. the rest of the variables in this
        cmiSecAssocEntry."
    ::= { cmiSecAssocEntry 3 }

cmiSecAlgorithmType OBJECT-TYPE
    SYNTAX          INTEGER  {
                        other(1),
                        md5(2),
                        hmacMD5(3)
                    }
    MAX-ACCESS      read-create
    STATUS          current
    DESCRIPTION
        "Type of authentication algorithm.

        other(1)     Any other authentication algorithm not
                     specified here.

        md5(2)       MD5 message-digest algorithm.

        hmacMD5(3)  HMAC MD5 message-digest algorithm."
    REFERENCE       "RFC-2002 - IP Mobility Support, section 3.5.1"
    DEFVAL          { md5 }
    ::= { cmiSecAssocEntry 4 }

cmiSecAlgorithmMode OBJECT-TYPE
    SYNTAX          INTEGER  {
                        other(1),
                        prefixSuffix(2)
                    }
    MAX-ACCESS      read-create
    STATUS          current
    DESCRIPTION
        "Security mode used by this algorithm.

        other(1)         Any other mode not specified here.

        prefixSuffix(2)  In this mode, data over which
                         authenticator value needs to be
                         calculated is preceded and followed
                         by the 128 bit shared secret key."
    REFERENCE       "RFC-2002 - IP Mobility Support, section 3.5.1"
    DEFVAL          { prefixSuffix }
    ::= { cmiSecAssocEntry 5 }

cmiSecKey OBJECT-TYPE
    SYNTAX          OCTET STRING (SIZE  (16))
    MAX-ACCESS      read-create
    STATUS          deprecated
    DESCRIPTION
        "The shared secret key for the security
        associations. Reading this object will always return
        zero length value."
    ::= { cmiSecAssocEntry 6 }

cmiSecReplayMethod OBJECT-TYPE
    SYNTAX          INTEGER  {
                        other(1),
                        timestamps(2),
                        nonces(3)
                    }
    MAX-ACCESS      read-create
    STATUS          current
    DESCRIPTION
        "The replay-protection method supported for this SPI
        within this Mobility Security Association.

        other(1)      Any other replay protection method not
                      specified here.

        timestamps(2) Timestamp based replay protection method.

        nonces(3)     Nonce based replay protection method."
    REFERENCE       "RFC-2002 - IP Mobility Support, section 5.6"
    DEFVAL          { timestamps }
    ::= { cmiSecAssocEntry 7 }

cmiSecStatus OBJECT-TYPE
    SYNTAX          RowStatus
    MAX-ACCESS      read-create
    STATUS          current
    DESCRIPTION
        "The row status for this table."
    ::= { cmiSecAssocEntry 8 }

cmiSecKey2 OBJECT-TYPE
    SYNTAX          OCTET STRING (SIZE  (0..16))
    MAX-ACCESS      read-create
    STATUS          current
    DESCRIPTION
        "The shared secret key for the security
        associations. Reading this object will always return
        zero length value. If the value is given in hex, it
        should be 16 bytes in length. If it is in ascii, it
        can vary from 1 to 16 characters."
    ::= { cmiSecAssocEntry 9 }



-- HA System Information

cmiHaSystemVersion OBJECT-TYPE
    SYNTAX          SnmpAdminString
    MAX-ACCESS      read-only
    STATUS          current
    DESCRIPTION
        "MobileIP HA Release Version"
    ::= { cmiHaSystem 1 }
-- Mobile IP security violation table

cmiSecViolationTable OBJECT-TYPE
    SYNTAX          SEQUENCE OF CmiSecViolationEntry
    MAX-ACCESS      not-accessible
    STATUS          current
    DESCRIPTION
        "A table containing information about security
        violations. This table provides the same information
        as mipSecViolationTable of MIP MIB. The only
        difference is that indices of the table are changed so
        that mobile nodes which are not identified by the IP
        address will also be included in the table."
    REFERENCE
        "RFC-2002 - IP Mobility Support, sections 3.6.2.1,
        3.7.2.1 and 3.8.2.1"
    ::= { cmiSecurity 3 }

cmiSecViolationEntry OBJECT-TYPE
    SYNTAX          CmiSecViolationEntry
    MAX-ACCESS      not-accessible
    STATUS          current
    DESCRIPTION
        "Information about one particular security violation."
    INDEX           {
                        cmiSecViolatorIdentifierType,
                        cmiSecViolatorIdentifier
                    }
    ::= { cmiSecViolationTable 1 }

CmiSecViolationEntry ::= SEQUENCE {
        cmiSecViolatorIdentifierType CmiEntityIdentifierType,
        cmiSecViolatorIdentifier     CmiEntityIdentifier,
        cmiSecTotalViolations        Counter32,
        cmiSecRecentViolationSPI     CmiSpi,
        cmiSecRecentViolationTime    TimeStamp,
        cmiSecRecentViolationIDLow   Unsigned32,
        cmiSecRecentViolationIDHigh  Unsigned32,
        cmiSecRecentViolationReason  INTEGER
}

cmiSecViolatorIdentifierType OBJECT-TYPE
    SYNTAX          CmiEntityIdentifierType
    MAX-ACCESS      not-accessible
    STATUS          current
    DESCRIPTION
        "The type of Violator's identifier."
    ::= { cmiSecViolationEntry 1 }

cmiSecViolatorIdentifier OBJECT-TYPE
    SYNTAX          CmiEntityIdentifier
    MAX-ACCESS      not-accessible
    STATUS          current
    DESCRIPTION
        "Violator's identifier. The violator is not necessary
        in the cmiSecAssocTable."
    ::= { cmiSecViolationEntry 2 }

cmiSecTotalViolations OBJECT-TYPE
    SYNTAX          Counter32
    MAX-ACCESS      read-only
    STATUS          current
    DESCRIPTION
        "Total number of security violations for this peer."
    ::= { cmiSecViolationEntry 3 }

cmiSecRecentViolationSPI OBJECT-TYPE
    SYNTAX          CmiSpi
    MAX-ACCESS      read-only
    STATUS          current
    DESCRIPTION
        "SPI of the most recent security violation for this
        peer. If the security violation is due to an
        identification mismatch, then this is the SPI from the
        Mobile-Home Authentication Extension.  If the security
        violation is due to an invalid authenticator, then
        this is the SPI from the offending authentication
        extension.  In all other cases, it should be set to
        zero."
    ::= { cmiSecViolationEntry 4 }

cmiSecRecentViolationTime OBJECT-TYPE
    SYNTAX          TimeStamp
    MAX-ACCESS      read-only
    STATUS          current
    DESCRIPTION
        "Time of the most recent security violation for this
        peer."
    ::= { cmiSecViolationEntry 5 }

cmiSecRecentViolationIDLow OBJECT-TYPE
    SYNTAX          Unsigned32 (0..4294967295)
    MAX-ACCESS      read-only
    STATUS          current
    DESCRIPTION
        "Low-order 32 bits of identification used in request or
        reply of the most recent security violation for this
        peer."
    ::= { cmiSecViolationEntry 6 }

cmiSecRecentViolationIDHigh OBJECT-TYPE
    SYNTAX          Unsigned32 (0..4294967295)
    MAX-ACCESS      read-only
    STATUS          current
    DESCRIPTION
        "High-order 32 bits of identification used in request
        or reply of the most recent security violation for
        this peer."
    ::= { cmiSecViolationEntry 7 }

cmiSecRecentViolationReason OBJECT-TYPE
    SYNTAX          INTEGER  {
                        noMobilitySecurityAssociation(1),
                        badAuthenticator(2),
                        badIdentifier(3),
                        badSPI(4),
                        missingSecurityExtension(5),
                        other(6)
                    }
    MAX-ACCESS      read-only
    STATUS          current
    DESCRIPTION
        "Reason for the most recent security violation for
        this peer."
    REFERENCE       "RFC-2002 - IP Mobility Support"
    ::= { cmiSecViolationEntry 8 }



-- Mobility Agent Registration Counters

cmiMaRegMaxInMinuteRegs OBJECT-TYPE
    SYNTAX          Counter32
    MAX-ACCESS      read-only
    STATUS          current
    DESCRIPTION
        "The maximum number of Registration Requests received
        in a minute by the mobility agent."
    ::= { cmiMaReg 1 }

cmiMaRegDateMaxRegsReceived OBJECT-TYPE
    SYNTAX          DateAndTime
    MAX-ACCESS      read-only
    STATUS          current
    DESCRIPTION
        "The time at which number of Registration Requests
        received in a minute by the mobility agent were
        maximum."
    ::= { cmiMaReg 2 }

cmiMaRegInLastMinuteRegs OBJECT-TYPE
    SYNTAX          Counter32
    MAX-ACCESS      read-only
    STATUS          current
    DESCRIPTION
        "The number of Registration Requests received in the
        last minute by the mobility agent."
    ::= { cmiMaReg 3 }

-- Mobile Node Discovery Group
--
-- Mobile node could store multiple agent advertisements, however,
-- only the most recently received agent advertisement information
-- is required to be made available to the manager station.

cmiMnAdvFlags OBJECT-TYPE
    SYNTAX          BITS {
                        gre(0),
                        minEnc(1),
                        foreignAgent(2),
                        homeAgent(3),
                        busy(4),
                        regRequired(5),
                        reverseTunnel(6)
                    }
    MAX-ACCESS      read-only
    STATUS          current
    DESCRIPTION
        "The flags are contained in the 7th byte in the
        extension of the most recently received mobility agent
        advertisement:
            gre
                -- Agent offers Generic Routing Encapsulation
            minEnc,
                -- Agent offers Minimal Encapsulation
            foreignAgent,
                -- Agent is a Foreign Agent
            homeAgent,
                -- Agent is a Home Agent
            busy,
                -- Foreign Agent is busy
            regRequired,
                -- FA registration is required
            reverseTunnel,
                -- Agent supports reverse tunneling."
    ::= { cmiMnRecentAdvReceived 1 }
-- Mobile Node Registration Group
--

-- Registration table of mobile node

cmiMnRegistrationTable OBJECT-TYPE
    SYNTAX          SEQUENCE OF CmiMnRegistrationEntry
    MAX-ACCESS      not-accessible
    STATUS          current
    DESCRIPTION
        "A table containing information about the mobile
        node's attempted registration(s).  The mobile node
        updates this table based upon Registration Requests
        sent and Registration Replies received in response to
        these requests.  Certain variables within this table
        are also updated when Registration Requests are
        retransmitted."
    ::= { cmiMnRegistration 1 }

cmiMnRegistrationEntry OBJECT-TYPE
    SYNTAX          CmiMnRegistrationEntry
    MAX-ACCESS      not-accessible
    STATUS          current
    DESCRIPTION
        "Information about one registration attempt."
    AUGMENTS           { mnRegistrationEntry  }

    ::= { cmiMnRegistrationTable 1 }

CmiMnRegistrationEntry ::= SEQUENCE {
        cmiMnRegFlags CmiRegistrationFlags
}

cmiMnRegFlags OBJECT-TYPE
    SYNTAX          CmiRegistrationFlags
    MAX-ACCESS      read-only
    STATUS          current
    DESCRIPTION
        "Registration flags sent by the mobile node.  It is the
        second byte in the Mobile IP Registration Request
        message."
    ::= { cmiMnRegistrationEntry 1 }



-- Mobile Router System Group

cmiMrReverseTunnel OBJECT-TYPE
    SYNTAX          TruthValue
    MAX-ACCESS      read-write
    STATUS          current
    DESCRIPTION
        "Specifies whether reverse tunneling is enabled on the
        mobile router or not."
    DEFVAL          { true }
    ::= { cmiMrSystem 1 }

cmiMrRedundancyGroup OBJECT-TYPE
    SYNTAX          SnmpAdminString
    MAX-ACCESS      read-write
    STATUS          current
    DESCRIPTION
        "Name of the redundancy group used to provide network
        availability for the mobile router."
    DEFVAL          { "" }
    ::= { cmiMrSystem 2 }

cmiMrMobNetTable OBJECT-TYPE
    SYNTAX          SEQUENCE OF CmiMrMobNetEntry
    MAX-ACCESS      not-accessible
    STATUS          current
    DESCRIPTION
        "A table containing information about all the networks
        for which mobility is provided by the mobile router."
    ::= { cmiMrSystem 3 }

cmiMrMobNetEntry OBJECT-TYPE
    SYNTAX          CmiMrMobNetEntry
    MAX-ACCESS      not-accessible
    STATUS          current
    DESCRIPTION
        "Details of a single mobile network on mobile router."
    INDEX           { cmiMrMobNetIfIndex }
    ::= { cmiMrMobNetTable 1 }

CmiMrMobNetEntry ::= SEQUENCE {
        cmiMrMobNetIfIndex  InterfaceIndex,
        cmiMrMobNetAddrType InetAddressType,
        cmiMrMobNetAddr     InetAddress,
        cmiMrMobNetPfxLen   InetAddressPrefixLength,
        cmiMrMobNetStatus   RowStatus
}

cmiMrMobNetIfIndex OBJECT-TYPE
    SYNTAX          InterfaceIndex
    MAX-ACCESS      not-accessible
    STATUS          current
    DESCRIPTION
        "The ifIndex value from Interfaces table of MIB II
        for the interface on the mobile router connected to the
        mobile network."
    ::= { cmiMrMobNetEntry 1 }

cmiMrMobNetAddrType OBJECT-TYPE
    SYNTAX          InetAddressType
    MAX-ACCESS      read-only
    STATUS          current
    DESCRIPTION
        "Represents the type of IP address stored in
        cmiMrMobNetAddr."
    ::= { cmiMrMobNetEntry 2 }

cmiMrMobNetAddr OBJECT-TYPE
    SYNTAX          InetAddress (SIZE  (4 | 16))
    MAX-ACCESS      read-only
    STATUS          current
    DESCRIPTION
        "IP address of the mobile network."
    ::= { cmiMrMobNetEntry 3 }

cmiMrMobNetPfxLen OBJECT-TYPE
    SYNTAX          InetAddressPrefixLength
    MAX-ACCESS      read-only
    STATUS          current
    DESCRIPTION
        "Prefix length associated with the mobile network
        ip address."
    ::= { cmiMrMobNetEntry 4 }

cmiMrMobNetStatus OBJECT-TYPE
    SYNTAX          RowStatus
    MAX-ACCESS      read-create
    STATUS          current
    DESCRIPTION
        "The row status for the mobile network entry."
    ::= { cmiMrMobNetEntry 5 }



cmiMrHaTunnelIfIndex OBJECT-TYPE
    SYNTAX          InterfaceIndexOrZero
    MAX-ACCESS      read-only
    STATUS          current
    DESCRIPTION
        "The ifIndex value from Interfaces table of MIB II for
        the tunnel interface (to HA) of the mobile router."
    ::= { cmiMrSystem 4 }
-- Mobile Router's home agent address list

cmiMrHATable OBJECT-TYPE
    SYNTAX          SEQUENCE OF CmiMrHAEntry
    MAX-ACCESS      not-accessible
    STATUS          current
    DESCRIPTION
        "A table containing additional parameters related to
        a home agent beyond that provided by MIP MIB mnHATable."
    ::= { cmiMrSystem 5 }

cmiMrHAEntry OBJECT-TYPE
    SYNTAX          CmiMrHAEntry
    MAX-ACCESS      not-accessible
    STATUS          current
    DESCRIPTION
        "Additional information about a particular entry in the
        mnHATable beyond that provided by MIP MIB mnHAEntry."
    AUGMENTS           { mnHAEntry  }

    ::= { cmiMrHATable 1 }

CmiMrHAEntry ::= SEQUENCE {
        cmiMrHAPriority Unsigned32,
        cmiMrHABest     TruthValue
}

cmiMrHAPriority OBJECT-TYPE
    SYNTAX          Unsigned32 (0..255)
    MAX-ACCESS      read-create
    STATUS          current
    DESCRIPTION
        "The priority for this home agent."
    DEFVAL          { 100 }
    ::= { cmiMrHAEntry 1 }

cmiMrHABest OBJECT-TYPE
    SYNTAX          TruthValue
    MAX-ACCESS      read-only
    STATUS          current
    DESCRIPTION
        "Indicates whether this home agent is the best (in terms
        of the priority or the configuration time, when
        multiple home agents have the same priority) or not.
        When it is true, the mobile router will try to register
        with this home agent first."
    ::= { cmiMrHAEntry 2 }


-- Mobile router interface table

cmiMrIfTable OBJECT-TYPE
    SYNTAX          SEQUENCE OF CmiMrIfEntry
    MAX-ACCESS      not-accessible
    STATUS          current
    DESCRIPTION
        "A table containing roaming/solicitation parameters
        for all roaming interfaces on the mobile router."
    ::= { cmiMrSystem 6 }

cmiMrIfEntry OBJECT-TYPE
    SYNTAX          CmiMrIfEntry
    MAX-ACCESS      not-accessible
    STATUS          current
    DESCRIPTION
        "Roaming/solicitation parameters for one interface."
    INDEX           { cmiMrIfIndex }
    ::= { cmiMrIfTable 1 }

CmiMrIfEntry ::= SEQUENCE {
        cmiMrIfIndex                   InterfaceIndex,
        cmiMRIfDescription             SnmpAdminString,
        cmiMrIfHoldDown                Unsigned32,
        cmiMrIfRoamPriority            Unsigned32,
        cmiMrIfSolicitPeriodic         TruthValue,
        cmiMrIfSolicitInterval         Unsigned32,
        cmiMrIfSolicitRetransInitial   Unsigned32,
        cmiMrIfSolicitRetransMax       Unsigned32,
        cmiMrIfSolicitRetransLimit     Unsigned32,
        cmiMrIfSolicitRetransCurrent   Unsigned32,
        cmiMrIfSolicitRetransRemaining Gauge32,
        cmiMrIfSolicitRetransCount     Counter32,
        cmiMrIfCCoaAddressType         InetAddressType,
        cmiMrIfCCoaAddress             InetAddress,
        cmiMrIfCCoaDefaultGwType       InetAddressType,
        cmiMrIfCCoaDefaultGw           InetAddress,
        cmiMrIfCCoaRegRetry            Unsigned32,
        cmiMrIfCCoaRegRetryRemaining   Gauge32,
        cmiMrIfStatus                  RowStatus,
        cmiMrIfCCoaRegistration        TruthValue,
        cmiMrIfCCoaOnly                TruthValue,
        cmiMrIfCCoaEnable              TruthValue,
        cmiMrIfRoamStatus              TruthValue,
        cmiMrIfRegisteredCoAType       InetAddressType,
        cmiMrIfRegisteredCoA           InetAddress,
        cmiMrIfRegisteredMaAddrType    InetAddressType,
        cmiMrIfRegisteredMaAddr        InetAddress,
        cmiMrIfHaTunnelIfIndex         InterfaceIndexOrZero,
        cmiMrIfID                      Unsigned32
}

cmiMrIfIndex OBJECT-TYPE
    SYNTAX          InterfaceIndex
    MAX-ACCESS      not-accessible
    STATUS          current
    DESCRIPTION
        "The ifIndex value from Interfaces table of
        MIB II for an interface on the Mobile router."
    ::= { cmiMrIfEntry 1 }

cmiMRIfDescription OBJECT-TYPE
    SYNTAX          SnmpAdminString
    MAX-ACCESS      read-create
    STATUS          current
    DESCRIPTION
        "Description of the access type for the mobile router
        interface."
    DEFVAL          { "" }
    ::= { cmiMrIfEntry 2 }

cmiMrIfHoldDown OBJECT-TYPE
    SYNTAX          Unsigned32 (0..3600)
    UNITS           "seconds"
    MAX-ACCESS      read-create
    STATUS          current
    DESCRIPTION
        "Waiting time after which mobile router registers to
        agents heard on this interface."
    DEFVAL          { 0 }
    ::= { cmiMrIfEntry 3 }

cmiMrIfRoamPriority OBJECT-TYPE
    SYNTAX          Unsigned32 (0..255)
    MAX-ACCESS      read-create
    STATUS          current
    DESCRIPTION
        "The priority value used to select an interface among
        multiple interfaces to send registration request."
    DEFVAL          { 100 }
    ::= { cmiMrIfEntry 4 }

cmiMrIfSolicitPeriodic OBJECT-TYPE
    SYNTAX          TruthValue
    MAX-ACCESS      read-create
    STATUS          current
    DESCRIPTION
        "Specifies whether periodic agent solicitation is
        enabled or not. If this object is set to true(1), the
        mobile router will send solicitations on this interface
        periodically according to other configured parameters."
    DEFVAL          { false }
    ::= { cmiMrIfEntry 5 }

cmiMrIfSolicitInterval OBJECT-TYPE
    SYNTAX          Unsigned32 (1..65535)
    UNITS           "seconds"
    MAX-ACCESS      read-create
    STATUS          current
    DESCRIPTION
        "The time interval after which a solicitation has to
        be sent once an agent advertisement is heard on the
        interface."
    DEFVAL          { 600 }
    ::= { cmiMrIfEntry 6 }

cmiMrIfSolicitRetransInitial OBJECT-TYPE
    SYNTAX          Unsigned32 (10..10000)
    UNITS           "milliseconds"
    MAX-ACCESS      read-create
    STATUS          current
    DESCRIPTION
        "The wait period before first retransmission of a
        solicitation when no agent advertisement is heard."
    DEFVAL          { 1000 }
    ::= { cmiMrIfEntry 7 }

cmiMrIfSolicitRetransMax OBJECT-TYPE
    SYNTAX          Unsigned32 (10..10000)
    UNITS           "milliseconds"
    MAX-ACCESS      read-create
    STATUS          current
    DESCRIPTION
        "This value specifies the maximum limit for the
        solicitation retransmission timeout. For each successive
        solicit message retransmission timeout period is twice
        the previous period."
    DEFVAL          { 5000 }
    ::= { cmiMrIfEntry 8 }

cmiMrIfSolicitRetransLimit OBJECT-TYPE
    SYNTAX          Unsigned32 (0..10)
    MAX-ACCESS      read-create
    STATUS          current
    DESCRIPTION
        "The maximum number of solicitation retransmissions
        allowed."
    DEFVAL          { 3 }
    ::= { cmiMrIfEntry 9 }

cmiMrIfSolicitRetransCurrent OBJECT-TYPE
    SYNTAX          Unsigned32 (10..10000)
    UNITS           "milliseconds"
    MAX-ACCESS      read-only
    STATUS          current
    DESCRIPTION
        "Current retransmission interval."
    ::= { cmiMrIfEntry 10 }

cmiMrIfSolicitRetransRemaining OBJECT-TYPE
    SYNTAX          Gauge32
    UNITS           "milliseconds"
    MAX-ACCESS      read-only
    STATUS          current
    DESCRIPTION
        "Time remaining before the current retransmission
        interval expires."
    ::= { cmiMrIfEntry 11 }

cmiMrIfSolicitRetransCount OBJECT-TYPE
    SYNTAX          Counter32
    MAX-ACCESS      read-only
    STATUS          current
    DESCRIPTION
        "The number of retransmissions of the solicitation."
    ::= { cmiMrIfEntry 12 }

cmiMrIfCCoaAddressType OBJECT-TYPE
    SYNTAX          InetAddressType
    MAX-ACCESS      read-only
    STATUS          current
    DESCRIPTION
        "Represents the type of IP address stored
        in cmiMrIfCCoaAddress."
    ::= { cmiMrIfEntry 13 }

cmiMrIfCCoaAddress OBJECT-TYPE
    SYNTAX          InetAddress
    MAX-ACCESS      read-only
    STATUS          current
    DESCRIPTION
        "Interface address to be used as a collocated
        care-of IP address.  Currently, the primary
        interface IP address is used as the CCoA."
    ::= { cmiMrIfEntry 14 }

cmiMrIfCCoaDefaultGwType OBJECT-TYPE
    SYNTAX          InetAddressType
    MAX-ACCESS      read-create
    STATUS          current
    DESCRIPTION
        "Represents the type of IP address stored
        in cmiMrIfCCoaDefaultGw."
    ::= { cmiMrIfEntry 15 }

cmiMrIfCCoaDefaultGw OBJECT-TYPE
    SYNTAX          InetAddress (SIZE  (4 | 16))
    MAX-ACCESS      read-create
    STATUS          current
    DESCRIPTION
        "Gateway IP address to be used with CCoA
        registrations on an interface other than serial
        interface with a static (fixed) IP address."
    ::= { cmiMrIfEntry 16 }

cmiMrIfCCoaRegRetry OBJECT-TYPE
    SYNTAX          Unsigned32 (1..65535)
    UNITS           "seconds"
    MAX-ACCESS      read-create
    STATUS          current
    DESCRIPTION
        "Time to wait between successive registration
        attempts after CCoA registration failure."
    DEFVAL          { 60 }
    ::= { cmiMrIfEntry 17 }

cmiMrIfCCoaRegRetryRemaining OBJECT-TYPE
    SYNTAX          Gauge32
    UNITS           "seconds"
    MAX-ACCESS      read-only
    STATUS          current
    DESCRIPTION
        "Time remaining before the current CCoA registration
        retry interval expires."
    ::= { cmiMrIfEntry 18 }

cmiMrIfStatus OBJECT-TYPE
    SYNTAX          RowStatus
    MAX-ACCESS      read-create
    STATUS          current
    DESCRIPTION
        "The row status for this table."
    ::= { cmiMrIfEntry 19 }

cmiMrIfCCoaRegistration OBJECT-TYPE
    SYNTAX          TruthValue
    MAX-ACCESS      read-only
    STATUS          current
    DESCRIPTION
        "This indicates the type of registraton
        mobile router will currently attempt
        on this interface. If cmiMrIfCCoaRegistration
        is false, the mobile router will attempt to
        register through a foreign agent. If
        cmiMrIfCCoaRegistration is true, the mobile
        router will attempt CCoA registration.
        cmiMrIfCCoaRegistration will be true when
        cmiMrIfCCoaOnly is set to true.
        cmiMrIfCCoaRegistration will also be true
        when cmiMrIfCCoaOnly is set to 'false' and
        foreign agent advertisements are not heard
        on the interface."
    ::= { cmiMrIfEntry 20 }

cmiMrIfCCoaOnly OBJECT-TYPE
    SYNTAX          TruthValue
    MAX-ACCESS      read-create
    STATUS          current
    DESCRIPTION
        "This specifies whether 'ccoa-only' state is
        enabled or not on this mobile router interface.
        When this variable is set to true,
        mobile router will attempt to register directly
        using a CCoA and will not attempt foreign agent
        registrations even if foreign agent advertisements
        are heard on this interface.  When set to false,
        the mobile router will attempt to register via a
        foreign agent whenever foreign agent advertisements
        are heard.  When foreign agent advertisements are
        not heard, then the interface will attempt CCoA
        registration."
    DEFVAL          { false }
    ::= { cmiMrIfEntry 21 }

cmiMrIfCCoaEnable OBJECT-TYPE
    SYNTAX          TruthValue
    MAX-ACCESS      read-create
    STATUS          current
    DESCRIPTION
        "This enables CCoA registrations on the mobile
        router interface.  When this object is set
        to false, the mobile router will attempt only
        foreign agent registrations on this interface.
        When this object is set to true, the interface
        is enabled for CCoA registration.  Depending on
        the value of the cmiMrIfCCoaOnly object, the
        mobile router may register with a CCoA or
        with a foreign agent."
    DEFVAL          { false }
    ::= { cmiMrIfEntry 22 }

cmiMrIfRoamStatus OBJECT-TYPE
    SYNTAX          TruthValue
    MAX-ACCESS      read-only
    STATUS          current
    DESCRIPTION
        "Indicates whether the mobile router is currently
        registered through this interface."
    ::= { cmiMrIfEntry 23 }

cmiMrIfRegisteredCoAType OBJECT-TYPE
    SYNTAX          InetAddressType
    MAX-ACCESS      read-only
    STATUS          current
    DESCRIPTION
        "Represents the type of address stored in
        cmiMrIfRegisteredCoA."
    ::= { cmiMrIfEntry 24 }

cmiMrIfRegisteredCoA OBJECT-TYPE
    SYNTAX          InetAddress
    MAX-ACCESS      read-only
    STATUS          current
    DESCRIPTION
        "Represents the care-of address registered
        by the mobile router through this interface.
        This will be zero when the mobile router is
        at home or not registered.  If the
        registration is through a foreign agent, this
        contains the foreign agent care-of address.
        If the registration uses a collocated care-of
        address, this contains the collocated care-of
        address."
    ::= { cmiMrIfEntry 25 }

cmiMrIfRegisteredMaAddrType OBJECT-TYPE
    SYNTAX          InetAddressType
    MAX-ACCESS      read-only
    STATUS          current
    DESCRIPTION
        "Represents the type of address stored in
        cmiMrIfRegisteredMaAddr."
    ::= { cmiMrIfEntry 26 }

cmiMrIfRegisteredMaAddr OBJECT-TYPE
    SYNTAX          InetAddress
    MAX-ACCESS      read-only
    STATUS          current
    DESCRIPTION
        "Represents the address of the mobility agent
        through which this mobile router interface is
        registered.  It contains the home agent
        address if registered using a collocated
        care-of address.  It contains the foreign
        agent address if registered through a foreign
        agent.  It is zero when the mobile router is
        at home or not registered."
    ::= { cmiMrIfEntry 27 }

cmiMrIfHaTunnelIfIndex OBJECT-TYPE
    SYNTAX          InterfaceIndexOrZero
    MAX-ACCESS      read-only
    STATUS          current
    DESCRIPTION
        "The ifIndex value from Interfaces table of MIB II for
        the tunnel interface (to home agent) of the mobile
        router through this roaming interface."
    ::= { cmiMrIfEntry 28 }

cmiMrIfID OBJECT-TYPE
    SYNTAX          Unsigned32
    MAX-ACCESS      read-only
    STATUS          current
    DESCRIPTION
        "A unique number identifying the roaming interface.
        This is also used as an unique identifier for the
        tunnel between home agent and mobile router."
    ::= { cmiMrIfEntry 29 }



-- MR Counters

cmiMrBetterIfDetected OBJECT-TYPE
    SYNTAX          Counter32
    MAX-ACCESS      read-only
    STATUS          current
    DESCRIPTION
        "Number of times that the mobile router has detected
        a better interface."
    ::= { cmiMrSystem 7 }

cmiMrTunnelPktsRcvd OBJECT-TYPE
    SYNTAX          Counter32
    MAX-ACCESS      read-only
    STATUS          current
    DESCRIPTION
        "Number of packets received on the MR-HA tunnel."
    ::= { cmiMrSystem 8 }

cmiMrTunnelPktsSent OBJECT-TYPE
    SYNTAX          Counter32
    MAX-ACCESS      read-only
    STATUS          current
    DESCRIPTION
        "Number of packets sent through the MR-HA tunnel."
    ::= { cmiMrSystem 9 }

cmiMrTunnelBytesRcvd OBJECT-TYPE
    SYNTAX          Counter32
    MAX-ACCESS      read-only
    STATUS          current
    DESCRIPTION
        "Number of bytes received on the MR-HA tunnel."
    ::= { cmiMrSystem 10 }

cmiMrTunnelBytesSent OBJECT-TYPE
    SYNTAX          Counter32
    MAX-ACCESS      read-only
    STATUS          current
    DESCRIPTION
        "Number of bytes sent through the MR-HA tunnel."
    ::= { cmiMrSystem 11 }

cmiMrRedStateActive OBJECT-TYPE
    SYNTAX          Counter32
    MAX-ACCESS      read-only
    STATUS          current
    DESCRIPTION
        "Number of times the redundancy state of the mobile
        router changed to active."
    ::= { cmiMrSystem 12 }

cmiMrRedStatePassive OBJECT-TYPE
    SYNTAX          Counter32
    MAX-ACCESS      read-only
    STATUS          current
    DESCRIPTION
        "Number of times the redundancy state of the mobile
        router changed to passive."
    ::= { cmiMrSystem 13 }

cmiMrCollocatedTunnel OBJECT-TYPE
    SYNTAX          INTEGER  {
                        single(1),
                        double(2)
                    }
    MAX-ACCESS      read-write
    STATUS          current
    DESCRIPTION
        "This indicates whether a single tunnel or
        dual tunnels will be created between MR and HA
        when the mobile router registers with a CCoA."
    DEFVAL          { single }
    ::= { cmiMrSystem 14 }

cmiMrMultiPath OBJECT-TYPE
    SYNTAX          TruthValue
    MAX-ACCESS      read-write
    STATUS          current
    DESCRIPTION
        "Specifies whether multiple path is enabled on the
        mobile router or not."
    DEFVAL          { false }
    ::= { cmiMrSystem 15 }

cmiMrMultiPathMetricType OBJECT-TYPE
    SYNTAX          CmiMultiPathMetricType
    MAX-ACCESS      read-write
    STATUS          current
    DESCRIPTION
        "Specifies the metric to use when multiple path
        is enabled on the mobile router."
    DEFVAL          { bandwidth }
    ::= { cmiMrSystem 16 }
-- Mobile Router Discovery Group

cmiMrMaAdvTable OBJECT-TYPE
    SYNTAX          SEQUENCE OF CmiMrMaAdvEntry
    MAX-ACCESS      not-accessible
    STATUS          current
    DESCRIPTION
        "A table with information related to all the agent
        advertisements heard by the mobile router."
    ::= { cmiMrDiscovery 1 }

cmiMrMaAdvEntry OBJECT-TYPE
    SYNTAX          CmiMrMaAdvEntry
    MAX-ACCESS      not-accessible
    STATUS          current
    DESCRIPTION
        "Information related to a single agent advertisement."
    INDEX           {
                        cmiMrMaAddressType,
                        cmiMrMaAddress
                    }
    ::= { cmiMrMaAdvTable 1 }

CmiMrMaAdvEntry ::= SEQUENCE {
        cmiMrMaAddressType          InetAddressType,
        cmiMrMaAddress              InetAddress,
        cmiMrMaIsHa                 TruthValue,
        cmiMrMaAdvRcvIf             InterfaceIndex,
        cmiMrMaIfMacAddress         MacAddress,
        cmiMrMaAdvSequence          Unsigned32,
        cmiMrMaAdvFlags             BITS,
        cmiMrMaAdvMaxRegLifetime    Unsigned32,
        cmiMrMaAdvMaxLifetime       Unsigned32,
        cmiMrMaAdvLifetimeRemaining Gauge32,
        cmiMrMaAdvTimeReceived      TimeStamp,
        cmiMrMaAdvTimeFirstHeard    TimeStamp,
        cmiMrMaHoldDownRemaining    Gauge32
}

cmiMrMaAddressType OBJECT-TYPE
    SYNTAX          InetAddressType
    MAX-ACCESS      not-accessible
    STATUS          current
    DESCRIPTION
        "Represents the type of IP address stored in
        cmiMrMaAddress. Only IPv4 address type is supported."
    ::= { cmiMrMaAdvEntry 1 }

cmiMrMaAddress OBJECT-TYPE
    SYNTAX          InetAddress (SIZE  (4 | 16))
    MAX-ACCESS      not-accessible
    STATUS          current
    DESCRIPTION
        "IP address of the mobile agent from which the
        advertisement was received. Only IPv4 addresses are
        supported."
    ::= { cmiMrMaAdvEntry 2 }

cmiMrMaIsHa OBJECT-TYPE
    SYNTAX          TruthValue
    MAX-ACCESS      read-only
    STATUS          current
    DESCRIPTION
        "Indicates whether the mobile agent is a home agent for
        the mobile router or not. If true, it means that the
        agent is one of the mobile router's configured home
        agents."
    ::= { cmiMrMaAdvEntry 3 }

cmiMrMaAdvRcvIf OBJECT-TYPE
    SYNTAX          InterfaceIndex
    MAX-ACCESS      read-only
    STATUS          current
    DESCRIPTION
        "The ifIndex value from Interfaces table of MIB II for
        the interface of mobile router on which the
        advertisement from the mobile agent was received."
    ::= { cmiMrMaAdvEntry 4 }

cmiMrMaIfMacAddress OBJECT-TYPE
    SYNTAX          MacAddress
    MAX-ACCESS      read-only
    STATUS          current
    DESCRIPTION
        "Mobile agent advertising interface MAC address."
    ::= { cmiMrMaAdvEntry 5 }

cmiMrMaAdvSequence OBJECT-TYPE
    SYNTAX          Unsigned32 (0..65535)
    MAX-ACCESS      read-only
    STATUS          current
    DESCRIPTION
        "The sequence number of the most recently received
        agent advertisement. The sequence number ranges from
        0 to 0xffff. After the sequence number attains the
        value 0xffff, it will roll over to 256."
    ::= { cmiMrMaAdvEntry 6 }

cmiMrMaAdvFlags OBJECT-TYPE
    SYNTAX          BITS {
                        reverseTunnel(0),
                        gre(1),
                        minEnc(2),
                        foreignAgent(3),
                        homeAgent(4),
                        busy(5),
                        regRequired(6)
                    }
    MAX-ACCESS      read-only
    STATUS          current
    DESCRIPTION
        "The flags contained in the 7th byte in the extension of
        the most recently received mobility agent advertisement:
            reverseTunnel,
                -- Agent supports reverse tunneling
            gre,
                -- Agent offers Generic Routing Encapsulation
            minEnc,
                -- Agent offers Minimal Encapsulation
            foreignAgent,
                -- Agent is a Foreign Agent
            homeAgent,
                -- Agent is a Home Agent
            busy,
                -- Foreign Agent is busy
            regRequired
                -- FA registration is required."
    ::= { cmiMrMaAdvEntry 7 }

cmiMrMaAdvMaxRegLifetime OBJECT-TYPE
    SYNTAX          Unsigned32 (1..65535)
    UNITS           "seconds"
    MAX-ACCESS      read-only
    STATUS          current
    DESCRIPTION
        "The longest registration lifetime in seconds that the
        agent is willing to accept in any registration request."
    ::= { cmiMrMaAdvEntry 8 }

cmiMrMaAdvMaxLifetime OBJECT-TYPE
    SYNTAX          Unsigned32 (1..65535)
    UNITS           "seconds"
    MAX-ACCESS      read-only
    STATUS          current
    DESCRIPTION
        "The maximum length of time that the Advertisement is
        considered valid in the absence of further
        Advertisements."
    REFERENCE       "AdvertisementLifeTime in RFC1256."
    ::= { cmiMrMaAdvEntry 9 }

cmiMrMaAdvLifetimeRemaining OBJECT-TYPE
    SYNTAX          Gauge32
    UNITS           "seconds"
    MAX-ACCESS      read-only
    STATUS          current
    DESCRIPTION
        "The time remaining for the advertisement lifetime
        expiration."
    ::= { cmiMrMaAdvEntry 10 }

cmiMrMaAdvTimeReceived OBJECT-TYPE
    SYNTAX          TimeStamp
    MAX-ACCESS      read-only
    STATUS          current
    DESCRIPTION
        "The time at which the most recently received
        advertisement was received."
    ::= { cmiMrMaAdvEntry 11 }

cmiMrMaAdvTimeFirstHeard OBJECT-TYPE
    SYNTAX          TimeStamp
    MAX-ACCESS      read-only
    STATUS          current
    DESCRIPTION
        "The time at which the first Advertisement from the
        mobile agent was received."
    ::= { cmiMrMaAdvEntry 12 }

cmiMrMaHoldDownRemaining OBJECT-TYPE
    SYNTAX          Gauge32
    UNITS           "seconds"
    MAX-ACCESS      read-only
    STATUS          current
    DESCRIPTION
        "The time remaining for the hold down period
        expiration."
    ::= { cmiMrMaAdvEntry 13 }



-- Mobile Router Registration Group

cmiMrRegExtendExpire OBJECT-TYPE
    SYNTAX          Unsigned32 (1..3600)
    UNITS           "seconds"
    MAX-ACCESS      read-write
    STATUS          current
    DESCRIPTION
        "Time in seconds before lifetime expiration to send
        registration request."
    ::= { cmiMrRegistration 1 }

cmiMrRegExtendRetry OBJECT-TYPE
    SYNTAX          Unsigned32 (0..10)
    MAX-ACCESS      read-write
    STATUS          current
    DESCRIPTION
        "The number of retries to be sent."
    ::= { cmiMrRegistration 2 }

cmiMrRegExtendInterval OBJECT-TYPE
    SYNTAX          Unsigned32 (1..3600)
    UNITS           "seconds"
    MAX-ACCESS      read-write
    STATUS          current
    DESCRIPTION
        "Time after which the mobile router is to send another
        registration request when no reply is received."
    ::= { cmiMrRegistration 3 }

cmiMrRegLifetime OBJECT-TYPE
    SYNTAX          Unsigned32 (3..65535)
    UNITS           "seconds"
    MAX-ACCESS      read-write
    STATUS          current
    DESCRIPTION
        "The requested lifetime in registration requests."
    ::= { cmiMrRegistration 4 }

cmiMrRegRetransInitial OBJECT-TYPE
    SYNTAX          Unsigned32 (10..10000)
    UNITS           "milli-seconds"
    MAX-ACCESS      read-write
    STATUS          current
    DESCRIPTION
        "Time to wait before retransmission for the first time
        when no reply is received."
    ::= { cmiMrRegistration 5 }

cmiMrRegRetransMax OBJECT-TYPE
    SYNTAX          Unsigned32 (10..10000)
    UNITS           "milli-seconds"
    MAX-ACCESS      read-write
    STATUS          current
    DESCRIPTION
        "Maximum retransmission time allowed."
    ::= { cmiMrRegistration 6 }

cmiMrRegRetransLimit OBJECT-TYPE
    SYNTAX          Unsigned32 (0..10)
    MAX-ACCESS      read-write
    STATUS          current
    DESCRIPTION
        "The maximum number of retransmissions allowed."
    ::= { cmiMrRegistration 7 }

cmiMrRegNewHa OBJECT-TYPE
    SYNTAX          Counter32
    MAX-ACCESS      read-only
    STATUS          current
    DESCRIPTION
        "The number of times MR registers with a different HA
        due to changes in HA / HA priority."
    ::= { cmiMrRegistration 8 }

-- MobileIP Notification Related Object Group

cmiTrapControl OBJECT-TYPE
    SYNTAX          BITS {
                        cmiMrStateChangeTrap(0),
                        cmiMrCoaChangeTrap(1),
                        cmiMrNewMATrap(2),
                        cmiHaMnRegFailedTrap(3),
                        cmiHaMaxBindingsNotif(4)
                    }
    MAX-ACCESS      read-write
    STATUS          current
    DESCRIPTION
        "An object to turn Mobile IP notification generation on
        and off. Setting a notification type's bit to 1 enables
        generation of notifications of that type, subject to
        further filtering resulting from entries in the
        snmpNotificationMIB.  Setting the bit to 0 disables
        generation of notifications of that type."
    DEFVAL          { {  } }
    ::= { cmiTrapObjects 1 }

cmiNtRegCOAType OBJECT-TYPE
    SYNTAX          InetAddressType
    MAX-ACCESS      read-only
    STATUS          current
    DESCRIPTION
        "Represents the type of the address stored in
        cmiHaRegMnCOA."
    ::= { cmiTrapObjects 3 }

cmiNtRegCOA OBJECT-TYPE
    SYNTAX          InetAddress
    MAX-ACCESS      read-only
    STATUS          current
    DESCRIPTION
        "The Mobile Node's Care-of address."
    ::= { cmiTrapObjects 4 }

cmiNtRegHAAddrType OBJECT-TYPE
    SYNTAX          InetAddressType
    MAX-ACCESS      read-only
    STATUS          current
    DESCRIPTION
        "Represents the type of the address stored in
        cmiHaRegMnHa."
    ::= { cmiTrapObjects 5 }

cmiNtRegHomeAgent OBJECT-TYPE
    SYNTAX          InetAddress
    MAX-ACCESS      read-only
    STATUS          current
    DESCRIPTION
        "The Mobile Node's Home Agent address."
    ::= { cmiTrapObjects 6 }

cmiNtRegHomeAddressType OBJECT-TYPE
    SYNTAX          InetAddressType
    MAX-ACCESS      read-only
    STATUS          current
    DESCRIPTION
        "Represents the type of the address stored in
        cmiHaRegRecentHomeAddress."
    ::= { cmiTrapObjects 7 }

cmiNtRegHomeAddress OBJECT-TYPE
    SYNTAX          IpAddress
    MAX-ACCESS      read-only
    STATUS          current
    DESCRIPTION
        "Home (IP) address of visiting mobile node."
    ::= { cmiTrapObjects 8 }

cmiNtRegNAI OBJECT-TYPE
    SYNTAX          OCTET STRING (SIZE  (1..255))
    MAX-ACCESS      read-only
    STATUS          current
    DESCRIPTION
        "The identifier associated with the mobile node."
    ::= { cmiTrapObjects 9 }

cmiNtRegDeniedCode OBJECT-TYPE
    SYNTAX          INTEGER  {
                        reasonUnspecified(128),
                        admProhibited(129),
                        insufficientResource(130),
                        mnAuthenticationFailure(131),
                        faAuthenticationFailure(132),
                        idMismatch(133),
                        poorlyFormedRequest(134),
                        tooManyBindings(135),
                        unknownHA(136),
                        reverseTunnelUnavailable(137),
                        reverseTunnelBitNotSet(138),
                        encapsulationUnavailable(139)
                    }
    MAX-ACCESS      read-only
    STATUS          current
    DESCRIPTION
        "The Code indicating the reason why the most recent
        Registration Request for this mobile node was rejected
        by the home agent."
    ::= { cmiTrapObjects 10 }
-- Notifications

ciscoMobileIpMIBNotifications  OBJECT IDENTIFIER
    ::= { ciscoMobileIpMIB 0 }


cmiMrStateChange NOTIFICATION-TYPE
    OBJECTS         { mnState }
    STATUS          current
    DESCRIPTION
        "The Mobile Router state change notification. This
        notification is sent when the Mobile Router has
        undergone a state change from its previous
        state of Mobile IP. Generation of this notification
        is controlled by the cmiTrapControl object."
   ::= { ciscoMobileIpMIBNotifications 1 }

cmiMrCoaChange NOTIFICATION-TYPE
    OBJECTS         {
                        mnRegCOA,
                        mnRegAgentAddress
                    }
    STATUS          current
    DESCRIPTION
        "The Mobile Router care-of-address change notification.
        This notification is sent when the Mobile Router has
        changed its care-of-address. Generation of this
        notification is controlled by the cmiTrapControl
        object."
   ::= { ciscoMobileIpMIBNotifications 2 }

cmiMrNewMA NOTIFICATION-TYPE
    OBJECTS         {
                        cmiMrMaIsHa,
                        cmiMrMaAdvFlags,
                        cmiMrMaAdvRcvIf
                    }
    STATUS          current
    DESCRIPTION
        "The Mobile Router new agent discovery notification.
        This notification is sent when the Mobile Router has
        heard an agent advertisement from a new mobile agent.
        Generation of this notification is controlled by the
        cmiTrapControl object."
   ::= { ciscoMobileIpMIBNotifications 3 }

cmiHaMnRegReqFailed NOTIFICATION-TYPE
    OBJECTS         {
                        cmiNtRegCOAType,
                        cmiNtRegCOA,
                        cmiNtRegHAAddrType,
                        cmiNtRegHomeAgent,
                        cmiNtRegHomeAddressType,
                        cmiNtRegHomeAddress,
                        cmiNtRegNAI,
                        cmiNtRegDeniedCode
                    }
    STATUS          current
    DESCRIPTION
        "The MN registration request failed notification.
        This notification is sent when the registration
        request from MN is rejected by Home Agent."
   ::= { ciscoMobileIpMIBNotifications 4 }

cmiHaMaxBindingsNotif NOTIFICATION-TYPE
    OBJECTS         {
                        cmiHaRegTotalMobilityBindings,
                        cmiHaMaximumBindings
                    }
    STATUS          current
    DESCRIPTION
        "This notification is generated when the registration
        request from an MN is rejected by the home agent, and
        the total number of registrations on the home agent
        has already reached the maximum number of allowed
        bindings represented by cmiHaMaximumBindings."
   ::= { ciscoMobileIpMIBNotifications 5 }
-- cmiMa Advertisement Group
--
-- Mobility agent advertisement configuration table

cmiMaAdvConfigTable OBJECT-TYPE
    SYNTAX          SEQUENCE OF CmiMaAdvConfigEntry
    MAX-ACCESS      not-accessible
    STATUS          current
    DESCRIPTION
        "A table containing configurable advertisement
        parameters for all advertisement interfaces in
        the mobility agent."
    ::= { cmiMaAdvertisement 1 }

cmiMaAdvConfigEntry OBJECT-TYPE
    SYNTAX          CmiMaAdvConfigEntry
    MAX-ACCESS      not-accessible
    STATUS          current
    DESCRIPTION
        "Advertisement parameters for one advertisement
        interface."
    INDEX           { cmiMaAdvInterfaceIndex }
    ::= { cmiMaAdvConfigTable 1 }

CmiMaAdvConfigEntry ::= SEQUENCE {
        cmiMaAdvInterfaceIndex           InterfaceIndex,
        cmiMaInterfaceAddressType        InetAddressType,
        cmiMaInterfaceAddress            InetAddress,
        cmiMaAdvMaxRegLifetime           Unsigned32,
        cmiMaAdvPrefixLengthInclusion    TruthValue,
        cmiMaAdvAddressType              InetAddressType,
        cmiMaAdvAddress                  InetAddress,
        cmiMaAdvMaxInterval              Unsigned32,
        cmiMaAdvMinInterval              Unsigned32,
        cmiMaAdvMaxAdvLifetime           Unsigned32,
        cmiMaAdvResponseSolicitationOnly TruthValue,
        cmiMaAdvStatus                   RowStatus
}

cmiMaAdvInterfaceIndex OBJECT-TYPE
    SYNTAX          InterfaceIndex
    MAX-ACCESS      not-accessible
    STATUS          current
    DESCRIPTION
        "The ifIndex value from Interfaces table of MIB II for
        the interface which is advertising."
    ::= { cmiMaAdvConfigEntry 1 }

cmiMaInterfaceAddressType OBJECT-TYPE
    SYNTAX          InetAddressType
    MAX-ACCESS      read-only
    STATUS          current
    DESCRIPTION
        "Represents the type of IP address stored in
        cmiMaInterfaceAddress."
    ::= { cmiMaAdvConfigEntry 2 }

cmiMaInterfaceAddress OBJECT-TYPE
    SYNTAX          InetAddress
    MAX-ACCESS      read-only
    STATUS          current
    DESCRIPTION
        "IP address for advertisement interface."
    ::= { cmiMaAdvConfigEntry 3 }

cmiMaAdvMaxRegLifetime OBJECT-TYPE
    SYNTAX          Unsigned32 (3..65535)
    UNITS           "seconds"
    MAX-ACCESS      read-create
    STATUS          current
    DESCRIPTION
        "The longest lifetime in seconds that mobility agent
        is willing to accept in any registration request."
    DEFVAL          { 36000 }
    ::= { cmiMaAdvConfigEntry 4 }

cmiMaAdvPrefixLengthInclusion OBJECT-TYPE
    SYNTAX          TruthValue
    MAX-ACCESS      read-create
    STATUS          current
    DESCRIPTION
        "Whether the advertisement should include the Prefix-
        Lengths Extension. If it is true, all advertisements
        sent over this interface should include the
        Prefix-Lengths Extension."
    DEFVAL          { false }
    ::= { cmiMaAdvConfigEntry 5 }

cmiMaAdvAddressType OBJECT-TYPE
    SYNTAX          InetAddressType
    MAX-ACCESS      read-create
    STATUS          current
    DESCRIPTION
        "Represents the type of IP address stored in
        cmiMaAdvAddress."
    ::= { cmiMaAdvConfigEntry 6 }

cmiMaAdvAddress OBJECT-TYPE
    SYNTAX          InetAddress
    MAX-ACCESS      read-create
    STATUS          current
    DESCRIPTION
        "The IP destination address to be used for
        advertisements sent from the interface. The only
        permissible values are the all-systems multicast
        address (224.0.0.1) or the limited-broadcast address
        (255.255.255.255). Default value is 224.0.0.1 if
        the router supports IP multicast on the interface,
        else 255.255.255.255"
    REFERENCE       "AdvertisementAddress in RFC1256."
    ::= { cmiMaAdvConfigEntry 7 }

cmiMaAdvMaxInterval OBJECT-TYPE
    SYNTAX          Unsigned32 (0 | 4..1800)
    UNITS           "seconds"
    MAX-ACCESS      read-create
    STATUS          current
    DESCRIPTION
        "The maximum time in seconds between successive
        transmissions of Agent Advertisements from this
        interface. The default value will be 600 seconds
        for an interface which uses IEEE 802 style
        headers and for ATM interface. In other cases,
        default value will be zero."
    REFERENCE       "MaxAdvertisementInterval in RFC1256."
    ::= { cmiMaAdvConfigEntry 8 }

cmiMaAdvMinInterval OBJECT-TYPE
    SYNTAX          Unsigned32 (0 | 3..1800)
    UNITS           "seconds"
    MAX-ACCESS      read-create
    STATUS          current
    DESCRIPTION
        "The minimum time in seconds between successive
        transmissions of Agent Advertisements from this
        interface. Default value is 0.75 *
        cmiMaAdvMaxInterval."
    REFERENCE       "MinAdvertisementInterval in RFC1256."
    ::= { cmiMaAdvConfigEntry 9 }

cmiMaAdvMaxAdvLifetime OBJECT-TYPE
    SYNTAX          Unsigned32 (0 | 4..9000)
    UNITS           "seconds"
    MAX-ACCESS      read-create
    STATUS          current
    DESCRIPTION
        "The time (in seconds) to be placed in the Lifetime
        field of the RFC 1256-portion of the Agent
        Advertisements sent over this interface. Default
        value is 3 * cmiMaAdvMaxInterval."
    REFERENCE       "AdvertisementLifetime in RFC1256."
    ::= { cmiMaAdvConfigEntry 10 }

cmiMaAdvResponseSolicitationOnly OBJECT-TYPE
    SYNTAX          TruthValue
    MAX-ACCESS      read-create
    STATUS          current
    DESCRIPTION
        "The flag indicates whether the advertisement from
        that interface should be sent only in response to an
        Agent Solicitation message. This value depends upon
        cmiMaAdvMaxInterval. If cmiMaAdvMaxInterval is
        zero, this value will be set to true. If this is set
        to True, then cmiMaAdvMaxInterval will be set to
        zero."
    ::= { cmiMaAdvConfigEntry 11 }

cmiMaAdvStatus OBJECT-TYPE
    SYNTAX          RowStatus
    MAX-ACCESS      read-create
    STATUS          current
    DESCRIPTION
        "The row status for the agent advertisement table. If
        this column status is 'active', the manager should not
        change any column in the row. Only
        cmiMaAdvInterfaceIndex is mandatory for creating a
        new row. The interface should already exist."
    ::= { cmiMaAdvConfigEntry 12 }


-- conformance information

ciscoMobileIpMIBConformance  OBJECT IDENTIFIER
    ::= { ciscoMobileIpMIB 3 }

ciscoMobileIpCompliances  OBJECT IDENTIFIER
    ::= { ciscoMobileIpMIBConformance 1 }

ciscoMobileIpGroups  OBJECT IDENTIFIER
    ::= { ciscoMobileIpMIBConformance 2 }


-- compliance statements

ciscoMobileIpCompliance MODULE-COMPLIANCE
    STATUS          obsolete
    DESCRIPTION
        "The compliance statement for management entities
        which implement the Cisco Mobile IP MIB. Superseded
        by ciscoMobileIPComplianceV12R02."
    MODULE          -- this module
    GROUP           ciscoMobileIpFaRegGroup
    DESCRIPTION
        "This group is mandatory for foreign agents."

    GROUP           ciscoMobileIpHaRegGroup
    DESCRIPTION
        "This group is mandatory for home agents."
    ::= { ciscoMobileIpCompliances 1 }

ciscoMobileIpComplianceV12R02 MODULE-COMPLIANCE
    STATUS          deprecated
    DESCRIPTION
        "The compliance statement for management entities
        which implement the Cisco Mobile IP MIB. Superseded
        by ciscoMobileIPComplianceV12R03."
    MODULE          -- this module
    GROUP           ciscoMobileIpFaRegGroupV12R02
    DESCRIPTION
        "This group is mandatory for foreign agents."

    GROUP           ciscoMobileIpHaRegGroupV12R02
    DESCRIPTION
        "This group is mandatory for home agents."

    GROUP           ciscoMobileIpHaRedunGroup
    DESCRIPTION
        "This group is mandatory for home agents with
        redundancy feature."

    GROUP           ciscoMobileIpSecAssocGroup
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."
    ::= { ciscoMobileIpCompliances 2 }

ciscoMobileIpComplianceV12R03 MODULE-COMPLIANCE
    STATUS          deprecated
    DESCRIPTION
        "The compliance statement for management entities
        which implement the Cisco Mobile IP MIB. Superseded
        by ciscoMobileIPComplianceV12R03r1"
    MODULE          -- this module
    GROUP           ciscoMobileIpFaRegGroupV12R03
    DESCRIPTION
        "This group is mandatory for foreign agents."

    GROUP           ciscoMobileIpHaRegGroupV12R03
    DESCRIPTION
        "This group is mandatory for home agents."

    GROUP           ciscoMobileIpHaRedunGroup
    DESCRIPTION
        "This group is mandatory for home agents with
        redundancy feature."

    GROUP           ciscoMobileIpSecAssocGroup
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."
    ::= { ciscoMobileIpCompliances 3 }

ciscoMobileIpComplianceV12R03r1 MODULE-COMPLIANCE
    STATUS          deprecated
    DESCRIPTION
        "The compliance statement for management entities
        which implement the Cisco Mobile IP MIB."
    MODULE          -- this module
    GROUP           ciscoMobileIpFaRegGroupV12R03r1
    DESCRIPTION
        "This group is mandatory for foreign agents."

    GROUP           ciscoMobileIpHaRegGroupV12R03r1
    DESCRIPTION
        "This group is mandatory for home agents."

    GROUP           ciscoMobileIpHaRedunGroup
    DESCRIPTION
        "This group is mandatory for home agents with
        redundancy feature."

    GROUP           ciscoMobileIpSecAssocGroup
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroup
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroup
    DESCRIPTION
        "This group is mandatory for Mobile IP entities
        which support notifications."

    GROUP           ciscoMobileIpMrNotificationGroup
    DESCRIPTION
        "This group is mandatory for mobile routers."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 4 }

ciscoMobileIpComplianceV12R04 MODULE-COMPLIANCE
    STATUS          deprecated
    DESCRIPTION
        "The compliance statement for management entities
        which implement the Cisco Mobile IP MIB."
    MODULE          -- this module
    GROUP           ciscoMobileIpFaRegGroupV12R03r1
    DESCRIPTION
        "This group is mandatory for foreign agents."

    GROUP           ciscoMobileIpHaRegGroupV12R03r1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroup
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroup
    DESCRIPTION
        "This group is mandatory for Mobile IP entities
        which support notifications."

    GROUP           ciscoMobileIpMrNotificationGroup
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 5 }

ciscoMobileIpComplianceV12R05 MODULE-COMPLIANCE
    STATUS          deprecated
    DESCRIPTION
        "The compliance statement for management entities
        which implement the Cisco Mobile IP MIB."
    MODULE          -- this module
    GROUP           ciscoMobileIpFaRegGroupV12R03r1
    DESCRIPTION
        "This group is mandatory for foreign agents."

    GROUP           ciscoMobileIpHaRegGroupV12R03r1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroupV1
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroup
    DESCRIPTION
        "This group is mandatory for Mobile IP entities
        which support notifications."

    GROUP           ciscoMobileIpMrNotificationGroup
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 6 }

ciscoMobileIpComplianceV12R06 MODULE-COMPLIANCE
    STATUS          deprecated
    DESCRIPTION
        "The compliance statement for management entities
        which implement the Cisco Mobile IP MIB."
    MODULE          -- this module
    GROUP           ciscoMobileIpFaRegGroupV12R03r1
    DESCRIPTION
        "This group is mandatory for foreign agents."

    GROUP           ciscoMobileIpHaRegGroupV12R03r1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroupV2
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroup
    DESCRIPTION
        "This group is mandatory for Mobile IP entities
        which support notifications."

    GROUP           ciscoMobileIpMrNotificationGroup
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 7 }

ciscoMobileIpComplianceV12R07 MODULE-COMPLIANCE
    STATUS          deprecated
    DESCRIPTION
        "The compliance statement for management entities
        which implement the Cisco Mobile IP MIB."
    MODULE          -- this module
    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroupV2
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroup
    DESCRIPTION
        "This group is mandatory for Mobile IP entities
        which support notifications."

    GROUP           ciscoMobileIpMrNotificationGroup
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 8 }

ciscoMobileIpComplianceV12R08 MODULE-COMPLIANCE
    STATUS          deprecated
    DESCRIPTION
        "The compliance statement for management entities
        which implement the Cisco Mobile IP MIB."
    MODULE          -- this module
    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroupV2
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."
    ::= { ciscoMobileIpCompliances 9 }

ciscoMobileIpComplianceV12R09 MODULE-COMPLIANCE
    STATUS          deprecated
    DESCRIPTION
        "The compliance statement for management entities
        which implement the Cisco Mobile IP MIB."
    MODULE          -- this module
    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpMrSystemGroupV3
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."

    OBJECT          cmiMrIfRegisteredCoAType
    SYNTAX          INTEGER  {
                        ipv4(1)
                    }
    DESCRIPTION
        "An implementation is only required to support
        IPv4 address type."

    OBJECT          cmiMrIfRegisteredCoA
    SYNTAX          InetAddress (SIZE (4))
    DESCRIPTION
        "An implementation is only required to support
        IPv4 addresses."

    OBJECT          cmiMrIfRegisteredMaAddrType
    SYNTAX          INTEGER  {
                        ipv4(1)
                    }
    DESCRIPTION
        "An implementation is only required to support
        IPv4 address type."

    OBJECT          cmiMrIfRegisteredMaAddr
    SYNTAX          InetAddress (SIZE (4))
    DESCRIPTION
        "An implementation is only required to support
        IPv4 addresses."
    ::= { ciscoMobileIpCompliances 10 }

ciscoMobileIpComplianceV12R10 MODULE-COMPLIANCE
    STATUS          deprecated
    DESCRIPTION
        "The compliance statement for management entities
        which implement the Cisco Mobile IP MIB."
    MODULE          -- this module
    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRegGroupV12R03r2Sup1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpHaMobNetGroupSup1
    DESCRIPTION
        "This group is mandatory for home agents
        with support for mobile networks."

    GROUP           ciscoMobileIpMrSystemGroupV3
    DESCRIPTION
        "This group is mandatory for mobile routers."

    GROUP           ciscoMobileIpMrSystemGroupV3Sup1
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."

    OBJECT          cmiMrIfRegisteredCoAType
    SYNTAX          INTEGER  {
                        ipv4(1)
                    }
    DESCRIPTION
        "An implementation is only required to support
        IPv4 address type."

    OBJECT          cmiMrIfRegisteredCoA
    SYNTAX          InetAddress (SIZE (4))
    DESCRIPTION
        "An implementation is only required to support
        IPv4 addresses."

    OBJECT          cmiMrIfRegisteredMaAddrType
    SYNTAX          INTEGER  {
                        ipv4(1)
                    }
    DESCRIPTION
        "An implementation is only required to support
        IPv4 address type."

    OBJECT          cmiMrIfRegisteredMaAddr
    SYNTAX          InetAddress (SIZE (4))
    DESCRIPTION
        "An implementation is only required to support
        IPv4 addresses."
    ::= { ciscoMobileIpCompliances 11 }

ciscoMobileIpComplianceV12R11 MODULE-COMPLIANCE
    STATUS          deprecated
    DESCRIPTION
        "The compliance statement for management entities
        which implement the Cisco Mobile IP MIB."
    MODULE          -- this module
    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRegGroupV12R03r2Sup1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpHaMobNetGroupSup1
    DESCRIPTION
        "This group is mandatory for home agents
        with support for mobile networks."

    GROUP           ciscoMobileIpMrSystemGroupV3
    DESCRIPTION
        "This group is mandatory for mobile routers."

    GROUP           ciscoMobileIpMrSystemGroupV3Sup1
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    GROUP           ciscoMobileIpHaRegGroupV12R03r2Sup2
    DESCRIPTION
        "This group is optional for home agents."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."

    OBJECT          cmiMrIfRegisteredCoAType
    SYNTAX          INTEGER  {
                        ipv4(1)
                    }
    DESCRIPTION
        "An implementation is only required to support
        IPv4 address type."

    OBJECT          cmiMrIfRegisteredCoA
    SYNTAX          InetAddress (SIZE (4))
    DESCRIPTION
        "An implementation is only required to support
        IPv4 addresses."

    OBJECT          cmiMrIfRegisteredMaAddrType
    SYNTAX          INTEGER  {
                        ipv4(1)
                    }
    DESCRIPTION
        "An implementation is only required to support
        IPv4 address type."

    OBJECT          cmiMrIfRegisteredMaAddr
    SYNTAX          InetAddress (SIZE (4))
    DESCRIPTION
        "An implementation is only required to support
        IPv4 addresses."
    ::= { ciscoMobileIpCompliances 12 }

ciscoMobileIpComplianceRev1 MODULE-COMPLIANCE
    STATUS          deprecated
    DESCRIPTION
        "The compliance statement for management entities
        which implement the Cisco Mobile IP MIB."
    MODULE          -- this module
    GROUP           ciscoMobileIpHaSystemGroupV1
    DESCRIPTION
        "This group is mandatory for home agents."

    GROUP           ciscoMobileIpHaRegGroupV1
    DESCRIPTION
        "This group is mandatory for home agents."

    GROUP           ciscoMobileIpMrNotificationGroupV3
    DESCRIPTION
        "This group is mandatory for mobile routers."

    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRegGroupV12R03r2Sup1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpHaMobNetGroupSup1
    DESCRIPTION
        "This group is mandatory for home agents
        with support for mobile networks."

    GROUP           ciscoMobileIpMrSystemGroupV3
    DESCRIPTION
        "This group is mandatory for mobile routers."

    GROUP           ciscoMobileIpMrSystemGroupV3Sup1
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    GROUP           ciscoMobileIpHaRegGroupV12R03r2Sup2
    DESCRIPTION
        "This group is optional for home agents."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."

    OBJECT          cmiMrIfRegisteredCoAType
    SYNTAX          INTEGER  {
                        ipv4(1)
                    }
    DESCRIPTION
        "An implementation is only required to support
        IPv4 address type."

    OBJECT          cmiMrIfRegisteredCoA
    SYNTAX          InetAddress (SIZE (4))
    DESCRIPTION
        "An implementation is only required to support
        IPv4 addresses."

    OBJECT          cmiMrIfRegisteredMaAddrType
    SYNTAX          INTEGER  {
                        ipv4(1)
                    }
    DESCRIPTION
        "An implementation is only required to support
        IPv4 address type."

    OBJECT          cmiMrIfRegisteredMaAddr
    SYNTAX          InetAddress (SIZE (4))
    DESCRIPTION
        "An implementation is only required to support
        IPv4 addresses."
    ::= { ciscoMobileIpCompliances 13 }

ciscoMobileIpComplianceRev2 MODULE-COMPLIANCE
    STATUS          current
    DESCRIPTION
        "The compliance statement for management entities
        which implement the Cisco Mobile IP MIB."
    MODULE          -- this module
    GROUP           ciscoMobileIpHaSystemGroupV1
    DESCRIPTION
        "This group is mandatory for home agents."

    GROUP           ciscoMobileIpHaRegGroupV1
    DESCRIPTION
        "This group is mandatory for home agents."

    GROUP           ciscoMobileIpMrNotificationGroupV3
    DESCRIPTION
        "This group is mandatory for mobile routers."

    GROUP           ciscoMobileIpFaRegGroupV12R03r2
    DESCRIPTION
        "This group is mandatory for foreign agents."

    GROUP           ciscoMobileIpHaRegGroupV12R03r2
    DESCRIPTION
        "This group is mandatory for home agents."

    GROUP           ciscoMobileIpHaRegGroupV12R03r2Sup1
    DESCRIPTION
        "This group is mandatory for home agents."

    GROUP           ciscoMobileIpHaRedunGroup
    DESCRIPTION
        "This group is mandatory for home agents with
        redundancy feature."

    GROUP           ciscoMobileIpSecAssocGroupV12R02
    DESCRIPTION
        "This group is mandatory for Mobile IP entities (MN,
        FA, and HA) which support security associations.
        Mobile Nodes and Home Agents must implement this
        group. Foreign Agents must implement this group if
        they maintain any security associations."

    GROUP           ciscoMobileIpSecViolationGroup
    DESCRIPTION
        "This group is mandatory for Mobile IP entities (MN,
        FA, and HA) that can log security violations."

    GROUP           ciscoMobileIpMaRegGroup
    DESCRIPTION
        "This group is mandatory for mobility agents."

    GROUP           ciscoMobileIpFaAdvertisementGroup
    DESCRIPTION
        "This group is mandatory for foreign agents."

    GROUP           ciscoMobileIpFaSystemGroup
    DESCRIPTION
        "This group is mandatory for foreign agents with
        reverse-tunnel/challenge/asymmetric-link-coa features."

    GROUP           ciscoMobileIpMnDiscoveryGroup
    DESCRIPTION
        "This group is mandatory for mobile nodes which
        require reverse-tunnel support."

    GROUP           ciscoMobileIpMnRegistrationGroup
    DESCRIPTION
        "This group is mandatory for mobile nodes which
        require reverse-tunnel support."

    GROUP           ciscoMobileIpHaMobNetGroup
    DESCRIPTION
        "This group is mandatory for home agents
        with support for mobile networks."

    GROUP           ciscoMobileIpHaMobNetGroupSup1
    DESCRIPTION
        "This group is mandatory for home agents
        with support for mobile networks."

    GROUP           ciscoMobileIpMrSystemGroupV3
    DESCRIPTION
        "This group is mandatory for mobile routers."

    GROUP           ciscoMobileIpMrSystemGroupV3Sup1
    DESCRIPTION
        "This group is mandatory for mobile routers."

    GROUP           ciscoMobileIpMrDiscoveryGroup
    DESCRIPTION
        "This group is mandatory for mobile routers."

    GROUP           ciscoMobileIpMrRegistrationGroup
    DESCRIPTION
        "This group is mandatory for mobile routers."

    GROUP           ciscoMobileIpTrapObjectsGroupV2
    DESCRIPTION
        "This group is mandatory for Mobile IP entities
        which support notifications."

    GROUP           ciscoMobileIpMrNotificationGroupV2
    DESCRIPTION
        "This group is mandatory for mobile routers."

    GROUP           cmiMaAdvertisementGroup
    DESCRIPTION
        "This group is mandatory for the mobility agents (HA
        and FA) since they must implement Agent
        Advertisement."

    GROUP           ciscoMobileIpHaRegGroupV12R03r2Sup2
    DESCRIPTION
        "This group is optional for home agents."

    GROUP           ciscoMobileIpHaRegIntervalStatsGroup
    DESCRIPTION
        "This group is mandatory for mobile routers."

    GROUP           ciscoMobileIpHaRegTunnelStatsGroup
    DESCRIPTION
        "This group is mandatory for mobile routers."

    OBJECT          cmiMrMobNetAddrType
    SYNTAX          INTEGER  {
                        ipv4(1)
                    }
    DESCRIPTION
        "An implementation is only required to support
        IPv4 address type."

    OBJECT          cmiMrMobNetAddr
    SYNTAX          InetAddress (SIZE (4))
    DESCRIPTION
        "An implementation is only required to support
        IPv4 addresses."

    OBJECT          cmiMrIfCCoaAddressType
    SYNTAX          INTEGER  {
                        ipv4(1)
                    }
    DESCRIPTION
        "An implementation is only required to support
        IPv4 address type."

    OBJECT          cmiMrIfCCoaAddress
    SYNTAX          InetAddress (SIZE (4))
    DESCRIPTION
        "An implementation is only required to support
        IPv4 addresses."

    OBJECT          cmiMrIfCCoaDefaultGwType
    SYNTAX          INTEGER  {
                        ipv4(1)
                    }
    DESCRIPTION
        "An implementation is only required to support
        IPv4 address type."

    OBJECT          cmiMrIfCCoaDefaultGw
    SYNTAX          InetAddress (SIZE (4))
    DESCRIPTION
        "An implementation is only required to support
        IPv4 addresses."

    OBJECT          cmiMrIfRegisteredCoAType
    SYNTAX          INTEGER  {
                        ipv4(1)
                    }
    DESCRIPTION
        "An implementation is only required to support
        IPv4 address type."

    OBJECT          cmiMrIfRegisteredCoA
    SYNTAX          InetAddress (SIZE (4))
    DESCRIPTION
        "An implementation is only required to support
        IPv4 addresses."

    OBJECT          cmiMrIfRegisteredMaAddrType
    SYNTAX          INTEGER  {
                        ipv4(1)
                    }
    DESCRIPTION
        "An implementation is only required to support
        IPv4 address type."

    OBJECT          cmiMrIfRegisteredMaAddr
    SYNTAX          InetAddress (SIZE (4))
    DESCRIPTION
        "An implementation is only required to support
        IPv4 addresses."

    OBJECT          cmiHaRegIntervalSize
    MIN-ACCESS      read-only
    DESCRIPTION
        "Write access is not mandatory."
    ::= { ciscoMobileIpCompliances 14 }

-- Units of conformance
--
-- obsolete groups

ciscoMobileIpFaRegGroup OBJECT-GROUP
    OBJECTS         { cmiFaRegTotalVisitors }
    STATUS          obsolete
    DESCRIPTION
        "A collection of objects providing management
        information for the registration function within
        a foreign agent. Superseded by
        ciscoMobileIpFaRegGroupV12R02."
    ::= { ciscoMobileIpGroups 1 }

ciscoMobileIpHaRegGroup OBJECT-GROUP
    OBJECTS         { cmiHaRegTotalMobilityBindings }
    STATUS          obsolete
    DESCRIPTION
        "A collection of objects providing management
        information for the registration function within
        a home agent. Superseded by
        ciscoMobileIpHaRegGroupV12R02."
    ::= { ciscoMobileIpGroups 2 }

-- deprecated groups

ciscoMobileIpFaRegGroupV12R02 OBJECT-GROUP
    OBJECTS         {
                        cmiFaRegTotalVisitors,
                        cmiFaRegVisitorHomeAddress,
                        cmiFaRegVisitorHomeAgentAddress,
                        cmiFaRegVisitorTimeGranted,
                        cmiFaRegVisitorTimeRemaining,
                        cmiFaRegVisitorRegFlags,
                        cmiFaRegVisitorRegIDLow,
                        cmiFaRegVisitorRegIDHigh,
                        cmiFaRegVisitorRegIsAccepted
                    }
    STATUS          deprecated
    DESCRIPTION
        "A collection of objects providing management
        information for the registration function within
        a foreign agent.  Superseded by
        ciscoMobileIpFaRegGroupV12R03."
    ::= { ciscoMobileIpGroups 3 }

ciscoMobileIpHaRegGroupV12R02 OBJECT-GROUP
    OBJECTS         {
                        cmiHaRegTotalMobilityBindings,
                        cmiHaRegMnIdentifierType,
                        cmiHaRegMnIdentifier,
                        cmiHaRegServAcceptedRequests,
                        cmiHaRegServDeniedRequests,
                        cmiHaRegOverallServTime,
                        cmiHaRegRecentServAcceptedTime,
                        cmiHaRegRecentServDeniedTime,
                        cmiHaRegRecentServDeniedCode,
                        cmiHaRegTotalProcLocRegs,
                        cmiHaRegMaxProcLocInMinRegs,
                        cmiHaRegDateMaxRegsProcLoc,
                        cmiHaRegProcLocInLastMinRegs,
                        cmiHaRegTotalProcByAAARegs,
                        cmiHaRegMaxProcByAAAInMinRegs,
                        cmiHaRegDateMaxRegsProcByAAA,
                        cmiHaRegProcAAAInLastByMinRegs,
                        cmiHaRegAvgTimeRegsProcByAAA,
                        cmiHaRegMaxTimeRegsProcByAAA
                    }
    STATUS          deprecated
    DESCRIPTION
        "A collection of objects providing management
        information for the registration function within
        a home agent.  Superseded by
        ciscoMobileIpHaRegGroupV12R03."
    ::= { ciscoMobileIpGroups 4 }

ciscoMobileIpFaRegGroupV12R03 OBJECT-GROUP
    OBJECTS         {
                        cmiFaRegTotalVisitors,
                        cmiFaRegVisitorHomeAddress,
                        cmiFaRegVisitorHomeAgentAddress,
                        cmiFaRegVisitorTimeGranted,
                        cmiFaRegVisitorTimeRemaining,
                        cmiFaRegVisitorRegFlags,
                        cmiFaRegVisitorRegIDLow,
                        cmiFaRegVisitorRegIDHigh,
                        cmiFaRegVisitorRegIsAccepted,
                        cmiFaInitRegRequestsReceived,
                        cmiFaInitRegRequestsDiscarded,
                        cmiFaInitRegRequestsRelayed,
                        cmiFaInitRegRequestsDenied,
                        cmiFaInitRegRepliesValidFromHA,
                        cmiFaInitRegRepliesValidRelayMN,
                        cmiFaReRegRequestsReceived,
                        cmiFaReRegRequestsDiscarded,
                        cmiFaReRegRequestsRelayed,
                        cmiFaReRegRequestsDenied,
                        cmiFaReRegRepliesValidFromHA,
                        cmiFaReRegRepliesValidRelayToMN,
                        cmiFaDeRegRequestsReceived,
                        cmiFaDeRegRequestsDiscarded,
                        cmiFaDeRegRequestsRelayed,
                        cmiFaDeRegRequestsDenied,
                        cmiFaDeRegRepliesValidFromHA,
                        cmiFaDeRegRepliesValidRelayToMN
                    }
    STATUS          deprecated
    DESCRIPTION
        "A collection of objects providing management
        information for the registration function within
        a foreign agent. Superseded by
        ciscoMobileIpFaRegGroupV12R03r1"
    ::= { ciscoMobileIpGroups 9 }

ciscoMobileIpHaRegGroupV12R03 OBJECT-GROUP
    OBJECTS         {
                        cmiHaRegTotalMobilityBindings,
                        cmiHaRegMnIdentifierType,
                        cmiHaRegMnIdentifier,
                        cmiHaRegServAcceptedRequests,
                        cmiHaRegServDeniedRequests,
                        cmiHaRegOverallServTime,
                        cmiHaRegRecentServAcceptedTime,
                        cmiHaRegRecentServDeniedTime,
                        cmiHaRegRecentServDeniedCode,
                        cmiHaRegTotalProcLocRegs,
                        cmiHaRegMaxProcLocInMinRegs,
                        cmiHaRegDateMaxRegsProcLoc,
                        cmiHaRegProcLocInLastMinRegs,
                        cmiHaRegTotalProcByAAARegs,
                        cmiHaRegMaxProcByAAAInMinRegs,
                        cmiHaRegDateMaxRegsProcByAAA,
                        cmiHaRegProcAAAInLastByMinRegs,
                        cmiHaRegAvgTimeRegsProcByAAA,
                        cmiHaRegMaxTimeRegsProcByAAA,
                        cmiHaRegRequestsReceived,
                        cmiHaRegRequestsDenied,
                        cmiHaRegRequestsDiscarded,
                        cmiHaEncapUnavailable,
                        cmiHaNAICheckFailures,
                        cmiHaInitRegRequestsReceived,
                        cmiHaInitRegRequestsAccepted,
                        cmiHaInitRegRequestsDenied,
                        cmiHaInitRegRequestsDiscarded,
                        cmiHaReRegRequestsReceived,
                        cmiHaReRegRequestsAccepted,
                        cmiHaReRegRequestsDenied,
                        cmiHaReRegRequestsDiscarded,
                        cmiHaDeRegRequestsReceived,
                        cmiHaDeRegRequestsAccepted,
                        cmiHaDeRegRequestsDenied,
                        cmiHaDeRegRequestsDiscarded
                    }
    STATUS          deprecated
    DESCRIPTION
        "A collection of objects providing management
        information for the registration function within
        a home agent. Superseded by
        ciscoMobileIpHaRegGroupV12R03r1"
    ::= { ciscoMobileIpGroups 10 }

ciscoMobileIpSecAssocGroup OBJECT-GROUP
    OBJECTS         {
                        cmiSecAssocsCount,
                        cmiSecAlgorithmType,
                        cmiSecAlgorithmMode,
                        cmiSecKey,
                        cmiSecReplayMethod,
                        cmiSecStatus
                    }
    STATUS          deprecated
    DESCRIPTION
        "A collection of objects providing the management
        information for security associations of Mobile IP
        entities. Superseded by
        ciscoMobileIpSecAssocGroupV12R02"
    ::= { ciscoMobileIpGroups 6 }

-- current groups

ciscoMobileIpHaRedunGroup OBJECT-GROUP
    OBJECTS         {
                        cmiHaRedunSentBUs,
                        cmiHaRedunFailedBUs,
                        cmiHaRedunReceivedBUAcks,
                        cmiHaRedunTotalSentBUs,
                        cmiHaRedunReceivedBUs,
                        cmiHaRedunSentBUAcks,
                        cmiHaRedunSentBIReqs,
                        cmiHaRedunFailedBIReqs,
                        cmiHaRedunTotalSentBIReqs,
                        cmiHaRedunReceivedBIReps,
                        cmiHaRedunDroppedBIReps,
                        cmiHaRedunSentBIAcks,
                        cmiHaRedunReceivedBIReqs,
                        cmiHaRedunSentBIReps,
                        cmiHaRedunFailedBIReps,
                        cmiHaRedunTotalSentBIReps,
                        cmiHaRedunReceivedBIAcks,
                        cmiHaRedunDroppedBIAcks,
                        cmiHaRedunSecViolations
                    }
    STATUS          current
    DESCRIPTION
        "A collection of objects providing management
        information for the redundancy function within
        a home agent."
    ::= { ciscoMobileIpGroups 5 }

ciscoMobileIpSecViolationGroup OBJECT-GROUP
    OBJECTS         {
                        cmiSecTotalViolations,
                        cmiSecRecentViolationSPI,
                        cmiSecRecentViolationTime,
                        cmiSecRecentViolationIDLow,
                        cmiSecRecentViolationIDHigh,
                        cmiSecRecentViolationReason
                    }
    STATUS          current
    DESCRIPTION
        "A collection of objects providing the management
        information for security violation logging of Mobile
        IP entities."
    ::= { ciscoMobileIpGroups 7 }

ciscoMobileIpMaRegGroup OBJECT-GROUP
    OBJECTS         {
                        cmiMaRegMaxInMinuteRegs,
                        cmiMaRegDateMaxRegsReceived,
                        cmiMaRegInLastMinuteRegs
                    }
    STATUS          current
    DESCRIPTION
        "A collection of objects providing the management
        information for the registration function within
        a mobility agent."
    ::= { ciscoMobileIpGroups 8 }

ciscoMobileIpFaRegGroupV12R03r1 OBJECT-GROUP
    OBJECTS         {
                        cmiFaRegTotalVisitors,
                        cmiFaRegVisitorHomeAddress,
                        cmiFaRegVisitorHomeAgentAddress,
                        cmiFaRegVisitorTimeGranted,
                        cmiFaRegVisitorTimeRemaining,
                        cmiFaRegVisitorRegIDLow,
                        cmiFaRegVisitorRegIDHigh,
                        cmiFaRegVisitorRegIsAccepted,
                        cmiFaRegVisitorRegFlagsRev1,
                        cmiFaRegVisitorChallengeValue,
                        cmiFaInitRegRequestsReceived,
                        cmiFaInitRegRequestsDiscarded,
                        cmiFaInitRegRequestsRelayed,
                        cmiFaInitRegRequestsDenied,
                        cmiFaInitRegRepliesValidFromHA,
                        cmiFaInitRegRepliesValidRelayMN,
                        cmiFaReRegRequestsReceived,
                        cmiFaReRegRequestsDiscarded,
                        cmiFaReRegRequestsRelayed,
                        cmiFaReRegRequestsDenied,
                        cmiFaReRegRepliesValidFromHA,
                        cmiFaReRegRepliesValidRelayToMN,
                        cmiFaDeRegRequestsReceived,
                        cmiFaDeRegRequestsDiscarded,
                        cmiFaDeRegRequestsRelayed,
                        cmiFaDeRegRequestsDenied,
                        cmiFaDeRegRepliesValidFromHA,
                        cmiFaDeRegRepliesValidRelayToMN,
                        cmiFaReverseTunnelUnavailable,
                        cmiFaReverseTunnelBitNotSet,
                        cmiFaMnTooDistant,
                        cmiFaDeliveryStyleUnsupported,
                        cmiFaUnknownChallenge,
                        cmiFaMissingChallenge,
                        cmiFaStaleChallenge,
                        cmiFaCvsesFromMnRejected,
                        cmiFaCvsesFromHaRejected,
                        cmiFaNvsesFromMnNeglected,
                        cmiFaNvsesFromHaNeglected
                    }
    STATUS          deprecated
    DESCRIPTION
        "A collection of objects providing management
        information for the registration function within
        a foreign agent."
    ::= { ciscoMobileIpGroups 11 }

ciscoMobileIpHaRegGroupV12R03r1 OBJECT-GROUP
    OBJECTS         {
                        cmiHaRegTotalMobilityBindings,
                        cmiHaRegMnIdentifierType,
                        cmiHaRegMnIdentifier,
                        cmiHaRegMobilityBindingRegFlags,
                        cmiHaRegServAcceptedRequests,
                        cmiHaRegServDeniedRequests,
                        cmiHaRegOverallServTime,
                        cmiHaRegRecentServAcceptedTime,
                        cmiHaRegRecentServDeniedTime,
                        cmiHaRegRecentServDeniedCode,
                        cmiHaRegTotalProcLocRegs,
                        cmiHaRegMaxProcLocInMinRegs,
                        cmiHaRegDateMaxRegsProcLoc,
                        cmiHaRegProcLocInLastMinRegs,
                        cmiHaRegTotalProcByAAARegs,
                        cmiHaRegMaxProcByAAAInMinRegs,
                        cmiHaRegDateMaxRegsProcByAAA,
                        cmiHaRegProcAAAInLastByMinRegs,
                        cmiHaRegAvgTimeRegsProcByAAA,
                        cmiHaRegMaxTimeRegsProcByAAA,
                        cmiHaRegRequestsReceived,
                        cmiHaRegRequestsDenied,
                        cmiHaRegRequestsDiscarded,
                        cmiHaEncapUnavailable,
                        cmiHaNAICheckFailures,
                        cmiHaInitRegRequestsReceived,
                        cmiHaInitRegRequestsAccepted,
                        cmiHaInitRegRequestsDenied,
                        cmiHaInitRegRequestsDiscarded,
                        cmiHaReRegRequestsReceived,
                        cmiHaReRegRequestsAccepted,
                        cmiHaReRegRequestsDenied,
                        cmiHaReRegRequestsDiscarded,
                        cmiHaDeRegRequestsReceived,
                        cmiHaDeRegRequestsAccepted,
                        cmiHaDeRegRequestsDenied,
                        cmiHaDeRegRequestsDiscarded,
                        cmiHaReverseTunnelUnavailable,
                        cmiHaReverseTunnelBitNotSet,
                        cmiHaEncapsulationUnavailable,
                        cmiHaCvsesFromMnRejected,
                        cmiHaCvsesFromFaRejected,
                        cmiHaNvsesFromMnNeglected,
                        cmiHaNvsesFromFaNeglected
                    }
    STATUS          deprecated
    DESCRIPTION
        "A collection of objects providing management
        information for the registration function within
        a home agent."
    ::= { ciscoMobileIpGroups 12 }

ciscoMobileIpFaAdvertisementGroup OBJECT-GROUP
    OBJECTS         {
                        cmiFaAdvertIsBusy,
                        cmiFaAdvertRegRequired,
                        cmiFaAdvertChallengeWindow,
                        cmiFaAdvertChallengeValue
                    }
    STATUS          current
    DESCRIPTION
        "A collection of objects providing supplemental
        management information for the Agent Advertisement
        function within a foreign agent."
    ::= { ciscoMobileIpGroups 13 }

ciscoMobileIpFaSystemGroup OBJECT-GROUP
    OBJECTS         {
                        cmiFaRevTunnelSupported,
                        cmiFaChallengeSupported,
                        cmiFaEncapDeliveryStyleSupported,
                        cmiFaReverseTunnelEnable,
                        cmiFaChallengeEnable,
                        cmiFaAdvertChallengeChapSPI,
                        cmiFaCoaInterfaceOnly,
                        cmiFaCoaTransmitOnly,
                        cmiFaCoaRegAsymLink
                    }
    STATUS          current
    DESCRIPTION
        "A collection of objects providing the supporting/
        enabled feature information within a foreign agent."
    ::= { ciscoMobileIpGroups 14 }

ciscoMobileIpMnDiscoveryGroup OBJECT-GROUP
    OBJECTS         { cmiMnAdvFlags }
    STATUS          current
    DESCRIPTION
        "Group which supports the recently changed Adv Flag"
    ::= { ciscoMobileIpGroups 15 }

ciscoMobileIpMnRegistrationGroup OBJECT-GROUP
    OBJECTS         { cmiMnRegFlags }
    STATUS          current
    DESCRIPTION
        "Group having information about Mn registration"
    ::= { ciscoMobileIpGroups 16 }

ciscoMobileIpHaMobNetGroup OBJECT-GROUP
    OBJECTS         {
                        cmiHaMrDynamic,
                        cmiHaMrStatus,
                        cmiHaMobNetDynamic,
                        cmiHaMobNetStatus
                    }
    STATUS          current
    DESCRIPTION
        "A collection of objects providing the management
        information related to mobile networks in a
        home agent."
    ::= { ciscoMobileIpGroups 17 }

ciscoMobileIpMrSystemGroup OBJECT-GROUP
    OBJECTS         {
                        cmiMrReverseTunnel,
                        cmiMrRedundancyGroup,
                        cmiMrMobNetAddrType,
                        cmiMrMobNetAddr,
                        cmiMrMobNetPfxLen,
                        cmiMrMobNetStatus,
                        cmiMrHaTunnelIfIndex,
                        cmiMrHAPriority,
                        cmiMrHABest,
                        cmiMRIfDescription,
                        cmiMrIfHoldDown,
                        cmiMrIfRoamPriority,
                        cmiMrIfSolicitPeriodic,
                        cmiMrIfSolicitInterval,
                        cmiMrIfSolicitRetransInitial,
                        cmiMrIfSolicitRetransMax,
                        cmiMrIfSolicitRetransLimit,
                        cmiMrIfSolicitRetransCurrent,
                        cmiMrIfSolicitRetransRemaining,
                        cmiMrIfSolicitRetransCount,
                        cmiMrIfCCoaAddressType,
                        cmiMrIfCCoaAddress,
                        cmiMrIfCCoaDefaultGwType,
                        cmiMrIfCCoaDefaultGw,
                        cmiMrIfCCoaRegRetry,
                        cmiMrIfCCoaRegRetryRemaining,
                        cmiMrIfStatus,
                        cmiMrBetterIfDetected,
                        cmiMrTunnelPktsRcvd,
                        cmiMrTunnelPktsSent,
                        cmiMrTunnelBytesRcvd,
                        cmiMrTunnelBytesSent,
                        cmiMrRedStateActive,
                        cmiMrRedStatePassive
                    }
    STATUS          deprecated
    DESCRIPTION
        "A collection of objects providing the management
        information in a mobile router."
    ::= { ciscoMobileIpGroups 18 }

ciscoMobileIpMrDiscoveryGroup OBJECT-GROUP
    OBJECTS         {
                        cmiMrMaIsHa,
                        cmiMrMaAdvRcvIf,
                        cmiMrMaIfMacAddress,
                        cmiMrMaAdvSequence,
                        cmiMrMaAdvFlags,
                        cmiMrMaAdvMaxRegLifetime,
                        cmiMrMaAdvMaxLifetime,
                        cmiMrMaAdvLifetimeRemaining,
                        cmiMrMaAdvTimeReceived,
                        cmiMrMaAdvTimeFirstHeard,
                        cmiMrMaHoldDownRemaining
                    }
    STATUS          current
    DESCRIPTION
        "A collection of objects providing the management
        information for the agent discovery function in a
        mobile router."
    ::= { ciscoMobileIpGroups 19 }

ciscoMobileIpMrRegistrationGroup OBJECT-GROUP
    OBJECTS         {
                        cmiMrRegExtendExpire,
                        cmiMrRegExtendRetry,
                        cmiMrRegExtendInterval,
                        cmiMrRegLifetime,
                        cmiMrRegRetransInitial,
                        cmiMrRegRetransMax,
                        cmiMrRegRetransLimit,
                        cmiMrRegNewHa
                    }
    STATUS          current
    DESCRIPTION
        "A collection of objects providing the management
        information for the registration function within
        a mobile router."
    ::= { ciscoMobileIpGroups 20 }

ciscoMobileIpTrapObjectsGroup OBJECT-GROUP
    OBJECTS         { cmiTrapControl }
    STATUS          deprecated
    DESCRIPTION
        "A collection of objects providing the management
        information related to notifications in Mobile IP
        entities."
    ::= { ciscoMobileIpGroups 21 }

ciscoMobileIpMrNotificationGroup NOTIFICATION-GROUP
   NOTIFICATIONS    {
                        cmiMrStateChange,
                        cmiMrCoaChange,
                        cmiMrNewMA
                    }
    STATUS          deprecated
    DESCRIPTION
        "Group of notifications on a Mobile Router."
    ::= { ciscoMobileIpGroups 22 }

ciscoMobileIpSecAssocGroupV12R02 OBJECT-GROUP
    OBJECTS         {
                        cmiSecAssocsCount,
                        cmiSecAlgorithmType,
                        cmiSecAlgorithmMode,
                        cmiSecReplayMethod,
                        cmiSecStatus,
                        cmiSecKey2
                    }
    STATUS          current
    DESCRIPTION
        "A collection of objects providing the management
        information for security associations of Mobile IP
        entities."
    ::= { ciscoMobileIpGroups 23 }

cmiMaAdvertisementGroup OBJECT-GROUP
    OBJECTS         {
                        cmiMaInterfaceAddressType,
                        cmiMaInterfaceAddress,
                        cmiMaAdvMaxRegLifetime,
                        cmiMaAdvPrefixLengthInclusion,
                        cmiMaAdvAddress,
                        cmiMaAdvAddressType,
                        cmiMaAdvMaxInterval,
                        cmiMaAdvMinInterval,
                        cmiMaAdvMaxAdvLifetime,
                        cmiMaAdvResponseSolicitationOnly,
                        cmiMaAdvStatus
                    }
    STATUS          current
    DESCRIPTION
        "A collection of objects providing management
        information for the Agent Advertisement function
        within mobility agents."
    ::= { ciscoMobileIpGroups 24 }

ciscoMobileIpMrSystemGroupV1 OBJECT-GROUP
    OBJECTS         {
                        cmiMrReverseTunnel,
                        cmiMrRedundancyGroup,
                        cmiMrMobNetAddrType,
                        cmiMrMobNetAddr,
                        cmiMrMobNetPfxLen,
                        cmiMrMobNetStatus,
                        cmiMrHaTunnelIfIndex,
                        cmiMrHAPriority,
                        cmiMrHABest,
                        cmiMRIfDescription,
                        cmiMrIfHoldDown,
                        cmiMrIfRoamPriority,
                        cmiMrIfSolicitPeriodic,
                        cmiMrIfSolicitInterval,
                        cmiMrIfSolicitRetransInitial,
                        cmiMrIfSolicitRetransMax,
                        cmiMrIfSolicitRetransLimit,
                        cmiMrIfSolicitRetransCurrent,
                        cmiMrIfSolicitRetransRemaining,
                        cmiMrIfSolicitRetransCount,
                        cmiMrIfCCoaAddressType,
                        cmiMrIfCCoaAddress,
                        cmiMrIfCCoaDefaultGwType,
                        cmiMrIfCCoaDefaultGw,
                        cmiMrIfCCoaRegRetry,
                        cmiMrIfCCoaRegRetryRemaining,
                        cmiMrIfStatus,
                        cmiMrIfCCoaRegistration,
                        cmiMrIfCCoaOnly,
                        cmiMrBetterIfDetected,
                        cmiMrTunnelPktsRcvd,
                        cmiMrTunnelPktsSent,
                        cmiMrTunnelBytesRcvd,
                        cmiMrTunnelBytesSent,
                        cmiMrRedStateActive,
                        cmiMrRedStatePassive,
                        cmiMrCollocatedTunnel
                    }
    STATUS          deprecated
    DESCRIPTION
        "A collection of objects providing the management
        information in a mobile router."
    ::= { ciscoMobileIpGroups 25 }

ciscoMobileIpMrSystemGroupV2 OBJECT-GROUP
    OBJECTS         {
                        cmiMrReverseTunnel,
                        cmiMrRedundancyGroup,
                        cmiMrMobNetAddrType,
                        cmiMrMobNetAddr,
                        cmiMrMobNetPfxLen,
                        cmiMrMobNetStatus,
                        cmiMrHaTunnelIfIndex,
                        cmiMrHAPriority,
                        cmiMrHABest,
                        cmiMRIfDescription,
                        cmiMrIfHoldDown,
                        cmiMrIfRoamPriority,
                        cmiMrIfSolicitPeriodic,
                        cmiMrIfSolicitInterval,
                        cmiMrIfSolicitRetransInitial,
                        cmiMrIfSolicitRetransMax,
                        cmiMrIfSolicitRetransLimit,
                        cmiMrIfSolicitRetransCurrent,
                        cmiMrIfSolicitRetransRemaining,
                        cmiMrIfSolicitRetransCount,
                        cmiMrIfCCoaAddressType,
                        cmiMrIfCCoaAddress,
                        cmiMrIfCCoaDefaultGwType,
                        cmiMrIfCCoaDefaultGw,
                        cmiMrIfCCoaRegRetry,
                        cmiMrIfCCoaRegRetryRemaining,
                        cmiMrIfStatus,
                        cmiMrIfCCoaRegistration,
                        cmiMrIfCCoaOnly,
                        cmiMrIfCCoaEnable,
                        cmiMrBetterIfDetected,
                        cmiMrTunnelPktsRcvd,
                        cmiMrTunnelPktsSent,
                        cmiMrTunnelBytesRcvd,
                        cmiMrTunnelBytesSent,
                        cmiMrRedStateActive,
                        cmiMrRedStatePassive,
                        cmiMrCollocatedTunnel
                    }
    STATUS          deprecated
    DESCRIPTION
        "A collection of objects providing the management
        information in a mobile router."
    ::= { ciscoMobileIpGroups 26 }

ciscoMobileIpFaRegGroupV12R03r2 OBJECT-GROUP
    OBJECTS         {
                        cmiFaRegTotalVisitors,
                        cmiFaRegVisitorHomeAddress,
                        cmiFaRegVisitorHomeAgentAddress,
                        cmiFaRegVisitorTimeGranted,
                        cmiFaRegVisitorTimeRemaining,
                        cmiFaRegVisitorRegIDLow,
                        cmiFaRegVisitorRegIDHigh,
                        cmiFaRegVisitorRegIsAccepted,
                        cmiFaRegVisitorRegFlagsRev1,
                        cmiFaRegVisitorChallengeValue,
                        cmiFaInitRegRequestsReceived,
                        cmiFaInitRegRequestsDiscarded,
                        cmiFaInitRegRequestsRelayed,
                        cmiFaInitRegRequestsDenied,
                        cmiFaInitRegRepliesValidFromHA,
                        cmiFaInitRegRepliesValidRelayMN,
                        cmiFaReRegRequestsReceived,
                        cmiFaReRegRequestsDiscarded,
                        cmiFaReRegRequestsRelayed,
                        cmiFaReRegRequestsDenied,
                        cmiFaReRegRepliesValidFromHA,
                        cmiFaReRegRepliesValidRelayToMN,
                        cmiFaDeRegRequestsReceived,
                        cmiFaDeRegRequestsDiscarded,
                        cmiFaDeRegRequestsRelayed,
                        cmiFaDeRegRequestsDenied,
                        cmiFaDeRegRepliesValidFromHA,
                        cmiFaDeRegRepliesValidRelayToMN,
                        cmiFaReverseTunnelUnavailable,
                        cmiFaReverseTunnelBitNotSet,
                        cmiFaMnTooDistant,
                        cmiFaDeliveryStyleUnsupported,
                        cmiFaUnknownChallenge,
                        cmiFaMissingChallenge,
                        cmiFaStaleChallenge,
                        cmiFaCvsesFromMnRejected,
                        cmiFaCvsesFromHaRejected,
                        cmiFaNvsesFromMnNeglected,
                        cmiFaNvsesFromHaNeglected,
                        cmiFaTotalRegRequests,
                        cmiFaTotalRegReplies,
                        cmiFaMnFaAuthFailures,
                        cmiFaMnAAAAuthFailures
                    }
    STATUS          current
    DESCRIPTION
        "A collection of objects providing management
        information for the registration function within
        a foreign agent."
    ::= { ciscoMobileIpGroups 27 }

ciscoMobileIpHaRegGroupV12R03r2 OBJECT-GROUP
    OBJECTS         {
                        cmiHaRegTotalMobilityBindings,
                        cmiHaRegMnIdentifierType,
                        cmiHaRegMnIdentifier,
                        cmiHaRegMobilityBindingRegFlags,
                        cmiHaRegServAcceptedRequests,
                        cmiHaRegServDeniedRequests,
                        cmiHaRegOverallServTime,
                        cmiHaRegRecentServAcceptedTime,
                        cmiHaRegRecentServDeniedTime,
                        cmiHaRegRecentServDeniedCode,
                        cmiHaRegTotalProcLocRegs,
                        cmiHaRegMaxProcLocInMinRegs,
                        cmiHaRegDateMaxRegsProcLoc,
                        cmiHaRegProcLocInLastMinRegs,
                        cmiHaRegTotalProcByAAARegs,
                        cmiHaRegMaxProcByAAAInMinRegs,
                        cmiHaRegDateMaxRegsProcByAAA,
                        cmiHaRegProcAAAInLastByMinRegs,
                        cmiHaRegAvgTimeRegsProcByAAA,
                        cmiHaRegMaxTimeRegsProcByAAA,
                        cmiHaRegRequestsReceived,
                        cmiHaRegRequestsDenied,
                        cmiHaRegRequestsDiscarded,
                        cmiHaEncapUnavailable,
                        cmiHaNAICheckFailures,
                        cmiHaInitRegRequestsReceived,
                        cmiHaInitRegRequestsAccepted,
                        cmiHaInitRegRequestsDenied,
                        cmiHaInitRegRequestsDiscarded,
                        cmiHaReRegRequestsReceived,
                        cmiHaReRegRequestsAccepted,
                        cmiHaReRegRequestsDenied,
                        cmiHaReRegRequestsDiscarded,
                        cmiHaDeRegRequestsReceived,
                        cmiHaDeRegRequestsAccepted,
                        cmiHaDeRegRequestsDenied,
                        cmiHaDeRegRequestsDiscarded,
                        cmiHaReverseTunnelUnavailable,
                        cmiHaReverseTunnelBitNotSet,
                        cmiHaEncapsulationUnavailable,
                        cmiHaCvsesFromMnRejected,
                        cmiHaCvsesFromFaRejected,
                        cmiHaNvsesFromMnNeglected,
                        cmiHaNvsesFromFaNeglected,
                        cmiHaMnHaAuthFailures,
                        cmiHaMnAAAAuthFailures
                    }
    STATUS          current
    DESCRIPTION
        "A collection of objects providing management
        information for the registration function within
        a home agent."
    ::= { ciscoMobileIpGroups 28 }

ciscoMobileIpTrapObjectsGroupV2 OBJECT-GROUP
    OBJECTS         {
                        cmiTrapControl,
                        cmiNtRegCOA,
                        cmiNtRegCOAType,
                        cmiNtRegHAAddrType,
                        cmiNtRegHomeAgent,
                        cmiNtRegHomeAddressType,
                        cmiNtRegHomeAddress,
                        cmiNtRegNAI,
                        cmiNtRegDeniedCode
                    }
    STATUS          current
    DESCRIPTION
        "A collection of objects providing the management
        information related to notifications in Mobile IP
        entities."
    ::= { ciscoMobileIpGroups 29 }

ciscoMobileIpMrNotificationGroupV2 NOTIFICATION-GROUP
   NOTIFICATIONS    {
                        cmiMrStateChange,
                        cmiMrCoaChange,
                        cmiMrNewMA,
                        cmiHaMnRegReqFailed
                    }
    STATUS          current
    DESCRIPTION
        "Group of notifications on a Mobile Router."
    ::= { ciscoMobileIpGroups 30 }

ciscoMobileIpMrSystemGroupV3 OBJECT-GROUP
    OBJECTS         {
                        cmiMrReverseTunnel,
                        cmiMrRedundancyGroup,
                        cmiMrMobNetAddrType,
                        cmiMrMobNetAddr,
                        cmiMrMobNetPfxLen,
                        cmiMrMobNetStatus,
                        cmiMrHaTunnelIfIndex,
                        cmiMrHAPriority,
                        cmiMrHABest,
                        cmiMRIfDescription,
                        cmiMrIfHoldDown,
                        cmiMrIfRoamPriority,
                        cmiMrIfSolicitPeriodic,
                        cmiMrIfSolicitInterval,
                        cmiMrIfSolicitRetransInitial,
                        cmiMrIfSolicitRetransMax,
                        cmiMrIfSolicitRetransLimit,
                        cmiMrIfSolicitRetransCurrent,
                        cmiMrIfSolicitRetransRemaining,
                        cmiMrIfSolicitRetransCount,
                        cmiMrIfCCoaAddressType,
                        cmiMrIfCCoaAddress,
                        cmiMrIfCCoaDefaultGwType,
                        cmiMrIfCCoaDefaultGw,
                        cmiMrIfCCoaRegRetry,
                        cmiMrIfCCoaRegRetryRemaining,
                        cmiMrIfStatus,
                        cmiMrIfCCoaRegistration,
                        cmiMrIfCCoaOnly,
                        cmiMrIfCCoaEnable,
                        cmiMrIfRoamStatus,
                        cmiMrIfRegisteredCoAType,
                        cmiMrIfRegisteredCoA,
                        cmiMrIfRegisteredMaAddrType,
                        cmiMrIfRegisteredMaAddr,
                        cmiMrBetterIfDetected,
                        cmiMrTunnelPktsRcvd,
                        cmiMrTunnelPktsSent,
                        cmiMrTunnelBytesRcvd,
                        cmiMrTunnelBytesSent,
                        cmiMrRedStateActive,
                        cmiMrRedStatePassive,
                        cmiMrCollocatedTunnel
                    }
    STATUS          current
    DESCRIPTION
        "A collection of objects providing the management
        information in a mobile router."
    ::= { ciscoMobileIpGroups 31 }

ciscoMobileIpHaRegGroupV12R03r2Sup1 OBJECT-GROUP
    OBJECTS         {
                        cmiHaRegMnIfDescription,
                        cmiHaRegMnIfBandwidth,
                        cmiHaRegMnIfID,
                        cmiHaRegMnIfPathMetricType
                    }
    STATUS          current
    DESCRIPTION
        "Additional objects for providing management
        information for the registration function within
        a home agent."
    ::= { ciscoMobileIpGroups 32 }

ciscoMobileIpHaMobNetGroupSup1 OBJECT-GROUP
    OBJECTS         {
                        cmiHaMrMultiPath,
                        cmiHaMrMultiPathMetricType
                    }
    STATUS          current
    DESCRIPTION
        "Additional objects providing the management
        information related to mobile networks in a
        home agent."
    ::= { ciscoMobileIpGroups 33 }

ciscoMobileIpMrSystemGroupV3Sup1 OBJECT-GROUP
    OBJECTS         {
                        cmiMrIfHaTunnelIfIndex,
                        cmiMrIfID,
                        cmiMrMultiPath,
                        cmiMrMultiPathMetricType
                    }
    STATUS          current
    DESCRIPTION
        "Additional objects providing the management
        information in a mobile router specific to
        multiple tunnels feature."
    ::= { ciscoMobileIpGroups 34 }

ciscoMobileIpHaRegGroupV12R03r2Sup2 OBJECT-GROUP
    OBJECTS         { cmiHaRegMobilityBindingMacAddress }
    STATUS          current
    DESCRIPTION
        "Additional objects for providing management
        information for the registration function within
        a home agent."
    ::= { ciscoMobileIpGroups 35 }

ciscoMobileIpHaSystemGroupV1 OBJECT-GROUP
    OBJECTS         { cmiHaSystemVersion }
    STATUS          current
    DESCRIPTION
        "A collection of objects providing the management
        information in a home agent."
    ::= { ciscoMobileIpGroups 36 }

ciscoMobileIpMrNotificationGroupV3 NOTIFICATION-GROUP
   NOTIFICATIONS    { cmiHaMaxBindingsNotif }
    STATUS          current
    DESCRIPTION
        "This group supplements ciscoMobileIpMrNotificationGroupV2
        with the Object cmiHaMaxBindingsNotif."
    ::= { ciscoMobileIpGroups 37 }

ciscoMobileIpHaRegGroupV1 OBJECT-GROUP
    OBJECTS         { cmiHaMaximumBindings }
    STATUS          current
    DESCRIPTION
        "This group supplements ciscoMobileIpHaRegGroupV13R03r2
        to provide the Object to configure the bindings on
        the home agent."
    ::= { ciscoMobileIpGroups 38 }

ciscoMobileIpHaRegIntervalStatsGroup OBJECT-GROUP
    OBJECTS         {
                        cmiHaRegIntervalSize,
                        cmiHaRegIntervalMaxActiveBindings,
                        cmiHaRegInterval3gpp2MaxActiveBindings,
                        cmiHaRegIntervalWimaxMaxActiveBindings
                    }
    STATUS          current
    DESCRIPTION
        "This collection of objects provide the management information
        related to the active bindings on the Home Agent."
    ::= { ciscoMobileIpGroups 39 }

ciscoMobileIpHaRegTunnelStatsGroup OBJECT-GROUP
    OBJECTS         {
                        cmiHaRegTunnelStatsTunnelType,
                        cmiHaRegTunnelStatsNumUsers,
                        cmiHaRegTunnelStatsDataRateInt,
                        cmiHaRegTunnelStatsInBitRate,
                        cmiHaRegTunnelStatsInPktRate,
                        cmiHaRegTunnelStatsInBytes,
                        cmiHaRegTunnelStatsInPkts,
                        cmiHaRegTunnelStatsOutBitRate,
                        cmiHaRegTunnelStatsOutPktRate,
                        cmiHaRegTunnelStatsOutBytes,
                        cmiHaRegTunnelStatsOutPkts
                    }
    STATUS          current
    DESCRIPTION
        "This collection of objects provide the statistics of all the
        active tunnels between HA and CoA."
    ::= { ciscoMobileIpGroups 40 }

END
