-- *****************************************************************
-- CISCO-DNS-CLIENT-CAPABILITY.my:
-- Cisco  CISCO-DNS-CLIENT-MIB AGENT-CAPABILITIES
--
-- Sept 2004, Arul Mozhi
--
-- Copyright (c) 2004 by Cisco Systems, Inc.
-- All rights reserved.
-- *****************************************************************

CISCO-DNS-CLIENT-CAPABILITY DEFINITIONS ::= BEGIN

IMPORTS
        MODULE-IDENTITY,
        Unsigned32
                FROM SNMPv2-SMI
        AGENT-CAPABILITIES
                FROM SNMPv2-CONF
        ciscoAgentCapability
                FROM CISCO-SMI;

ciscoDNSClientCapability MODULE-IDENTITY
        LAST-UPDATED    "200411250000Z"
        ORGANIZATION    "Cisco Systems, Inc."
        CONTACT-INFO
                "       Cisco Systems
                        Customer Service

                Postal: 170 West Tasman Drive
                        San Jose, CA  95134
                        USA

                   Tel: +1 800 553-NETS

                E-mail: cs-san@cisco.com"
        DESCRIPTION
                "The capabilities description of
                CISCO-DNS-CLIENT-MIB."

        REVISION        "200411250000Z"
        DESCRIPTION
                "Added the agent capabilities
                 'cDNSClientCapSanOSV20R1MDS9000' for
                 SanOS 2.0(1) on Cisco MDS 9000 series devices."
        REVISION        "200408100000Z"
        DESCRIPTION
                "Initial version of this MIB module."
        ::= { ciscoAgentCapability 888 }

cDNSClientCapSanOSV20R1MDS9000 AGENT-CAPABILITIES
    PRODUCT-RELEASE      "Cisco SanOS 2.0(1) on Cisco MDS 9000
                          series devices."
    STATUS          current
    DESCRIPTION     "Cisco DNS Client MIB capabilities"

    SUPPORTS        CISCO-DNS-CLIENT-MIB
    INCLUDES        {
                         ciscoDNSServerConfigGroup ,
                         ciscoDNSDomainNameConfigGroup
                    }

        VARIATION        cdcNoOfDNSServerConfig
            SYNTAX       Unsigned32 (0..6)
            DESCRIPTION  "Implementation supports only maximum of
                          6 DNS Server configuration entries in
                          the system.
                          If there are already 6 dns entries configured
                          in the system, then new entry creation for
                          'cdcDNSServerTable' will fail."
    ::= { ciscoDNSClientCapability 1 }

END
