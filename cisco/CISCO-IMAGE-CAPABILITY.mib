-- *****************************************************************
-- CISCO-IMAGE-CAPABILITY.my: CISCO-IMAGE-MIB AGENT-CAPABILITIES
--
-- Jan 1995, Yunsen Wang
--
-- Sep 2003, Wen Xu
--
-- Mar 2009, Narendra B
--
-- Copyright (c) 1995, 2003, 2009 by cisco Systems Inc.
-- All rights reserved.
--
-- *****************************************************************

CISCO-IMAGE-CAPABILITY DEFINITIONS ::= BEGIN

IMPORTS
    MODULE-IDENTITY
        FROM SNMPv2-SMI
    AGENT-CAPABILITIES
        FROM SNMPv2-CONF
    ciscoAgentCapability
        FROM CISCO-SMI;


ciscoImageMIBCapability MODULE-IDENTITY
    LAST-UPDATED    "200903260000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com
            cs-snmp@cisco.com"
    DESCRIPTION
        "Agent capabilities for CISCO-IMAGE-MIB."
    REVISION        "200903260000Z"
    DESCRIPTION
        "Added ciscoImageCapabilityGssV03R01
        agent capabilities for Global Site
        Selector(GSS) release 3.1(0)."
    REVISION        "200309150000Z"
    DESCRIPTION
        "-- Add the capabilities of IOS
        versions 12.1(19E) and 12.2(17SX)
        for Catalyst 6000/6500 and Cisco 7600
        series devices.
        -- Add the capability of CatOS
        version 8.1(1)."
    REVISION        "199501250000Z"
    DESCRIPTION
        "Initial version of this MIB module."
    ::= { ciscoAgentCapability 580 }



ciscoImageMIBCapabilityV10R01 AGENT-CAPABILITIES
    PRODUCT-RELEASE "Cisco IOS 10.2"
    STATUS          current
    DESCRIPTION
        "ciscoImageMIB capabilites"

    SUPPORTS        CISCO-IMAGE-MIB
    INCLUDES        { ciscoImageMIBGroup }
    ::= { ciscoImageMIBCapability 1 }

ciscoImageCapabilityV12R0119ECat6K AGENT-CAPABILITIES
    PRODUCT-RELEASE "Cisco IOS 12.1(19E) on Catalyst 6000/6500
                      and Cisco 7600 series devices."
    STATUS          current
    DESCRIPTION
        "CISCO-IMAGE-MIB capabilities."

    SUPPORTS        CISCO-IMAGE-MIB
    INCLUDES        { ciscoImageMIBGroup }
    ::= { ciscoImageMIBCapability 2 }

ciscoImageCapabilityV12R0217SXCat6K AGENT-CAPABILITIES
    PRODUCT-RELEASE "Cisco IOS 12.2(17SX) on Catalyst 6000/6500
                      and Cisco 7600 series devices."
    STATUS          current
    DESCRIPTION
        "CISCO-IMAGE-MIB capabilities."

    SUPPORTS        CISCO-IMAGE-MIB
    INCLUDES        { ciscoImageMIBGroup }
    ::= { ciscoImageMIBCapability 3 }

ciscoImageCapabilityCatOSV08R0101 AGENT-CAPABILITIES
    PRODUCT-RELEASE "Cisco CatOS 8.1(1)."
    STATUS          current
    DESCRIPTION
        "CISCO-IMAGE-MIB capabilities."

    SUPPORTS        CISCO-IMAGE-MIB
    INCLUDES        { ciscoImageMIBGroup }
    ::= { ciscoImageMIBCapability 4 }

ciscoImageCapabilityGssV03R01 AGENT-CAPABILITIES
    PRODUCT-RELEASE "Global Site Selector(GSS) 3.1(0)"
    STATUS          current
    DESCRIPTION
        "CISCO-IMAGE-MIB capabilities for GSS 3.1(0)"

    SUPPORTS        CISCO-IMAGE-MIB
    INCLUDES        { ciscoImageMIBGroup }
    ::= { ciscoImageMIBCapability 5 }

END
