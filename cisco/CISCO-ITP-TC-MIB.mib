-- *****************************************************************
-- CISCO-ITP-TC-MIB: Mib for SS7 SP support entities
--
-- June 2001,  John Linton, Shekhar Acharya
--
-- Copyright (c) 2001, 2002-2003, 2004 by Cisco Systems, Inc.
-- All rights reserved.
-- *****************************************************************
CISCO-ITP-TC-MIB DEFINITIONS ::= BEGIN

IMPORTS
        Integer32,
        MODULE-IDENTITY,
        Unsigned32
                FROM SNMPv2-SMI

        TEXTUAL-CONVENTION
                FROM SNMPv2-TC

        ciscoMgmt
                FROM CISCO-SMI;

        ciscoItpTextualConventions MODULE-IDENTITY
        LAST-UPDATED    "200404260000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"

        DESCRIPTION
               "The defines textual conventions used by to manage
                devices related to the SS7 network.  The
                relevant ITU documents describing this technology is
                the ITU Q series, including ITU Q.700: Introduction to
                CCITT Signalling System No. 7 and ITU Q.701 Functional
                description of the message transfer part (MTP) of
                Signalling System No. 7.

        Abbreviations:
          CDPA  - Called Party Point Code
          CGPA  - Calling Party Point Code
          CLLI  - Common Language Location Codes
          CR    - Connection Request message
          CREF  - Connection Refusal message
          DPC   - Destination Point Code
          ERR   - Error message
          GTA   - Global Title Address
          GTI   - Global Title Indicator
          GTT   - Global Title Translation
          LUDT  - long unitdata message
          LUDTS - long unitdata service message
          M2PA  - MTP2 Peer-to-Peer Adaptation Layer
          M3UA  - MTP3-User Adaptation
          MAP   - Mated Application Table
          MSU   - Message Signal Unit
          MTP   - Message Transport Protocol
          MTP2  - Layer 2 of Message Transport Protocol
          MTP3  - Layer 3 of Message Transport Protocol
          NAI   - Nature of Address Indicator
          NP    - Numbering Plan
          NTT   - The Japanese Nippon Telephone & Telegraph
          OPC   - Originating Point Code
          PC    - Point Code
          RTN   - Route Table Name
          RSR   - Reset Request message
          SCCP  - Signalling Connection Control Part
          SCTP  - Stream Transmission Protocol(RFC 2960)
          SI    - Signalling Indicator
          SP    - Signalling Point
          SLC   - Signalling Link Code
          SLS   - Signalling Link Selector
          SSN   - Subsystem Number
          SUA   - SCCP-User Adaptation
          TFR   - Transfer Restricted messages
          TT    - Title Translation
          TTC   - The Japanese Telecommunications Technology
                  Committee
          UDT   - unitdata message
          UDTS  - unitdata service message
          XUDT  - extended unitdata message
          XUDTS - extended unitdata service message
        "
        REVISION        "200404260000Z"
        DESCRIPTION
                "Updated CItpTcPointCodeType to allow M3UA and
                 SUA point-code types."

        REVISION        "200308030000Z"
        DESCRIPTION
                "Updated CItpTcPointCode textual convention to
                 include descriptions for Japanese NTT and TTC
                 variants."

        REVISION        "200301290000Z"
        DESCRIPTION
                "Added textual convention used to support the
                 ability to define multiple instances of the
                 signalling points.  The following textual conventions
                 were added.
                    CItpTcNetworkName
                    CItpTcInstanceNumber
                    CItpTcSls

                 Also deprecated CItpTcGtaAddr and CItpTcGtaDisplayZB.
                 Added CItpTcGtaLongAddr and CItpTcGtaLongDisplay.

                 Added new enumerated value to CItpTcLinkType object
                 for virtual link used to connect signalling points
                 acting as gateways."

        REVISION        "200112110000Z"

        DESCRIPTION
                "Added new enumerated value to CItpTcLinkType object
                 for high speed link support. Add new enumerated
                 value to the CItpTcSs7Variant object to support
                 China national variant. A new textual convention has
                 been added to address 0..15 range for Global Title
                 addresses."

        REVISION        "200110010000Z"
        DESCRIPTION
                "Initial version of this MIB module."
        ::= { ciscoMgmt  231 }


--  ********************************************************************
--  *                                                                  *
--  * Textual Conventions                                              *
--  *                                                                  *
--  ********************************************************************
CItpTcAclId ::= TEXTUAL-CONVENTION
        STATUS          current
        DESCRIPTION
            "An numeric Identifier used to specify an access list
             used to permit and deny packets based on MTP3
             information. Either the value 0 or the value of access list
             identifier. A value of zero indicates that an access list
             is not specified."
        SYNTAX Unsigned32 (0 | 2700..2999)

CItpTcCLLI ::= TEXTUAL-CONVENTION
        STATUS          current
        DESCRIPTION
            "Common Language Location Codes (CLLI Codes).
             An 11-character standardized geographic identifier
             that uniquely identifies the geographic location of
             telecommunication equipment.

             The CLLI code is supported as octet string containing
             administrative information in human-readable form.

             The use of control codes should be avoided.

             The use of newline should be avoided.

             The use of leading or trailing white space should
             be avoided."
        REFERENCE
            "Complete listings of geographical and geopolitical
             codes can be found in the BR 751-401-xxx series and
             BR 751-100-055, respectively."
        SYNTAX OCTET STRING ( SIZE ( 0..11 ) )

CItpTcDisplayPC ::= TEXTUAL-CONVENTION
        STATUS          current
        DESCRIPTION
            "The Point Code in formatted based on the variant
             and the customer defined parameters."
        SYNTAX OCTET STRING ( SIZE ( 1..12 ) )

CItpTcEncodingSchemeValue ::= TEXTUAL-CONVENTION
        STATUS          current
        DESCRIPTION
                "The encoding scheme value."
        SYNTAX Integer32 (0..15)

CItpTcGlobalTitleSelector ::= TEXTUAL-CONVENTION
        STATUS          current
        DESCRIPTION
           "Global Title Selector.
            'nai'       : Global title translation based on
                          nature of address indicator.

            'tt'        : Global title translation based on
                          translation type.

            'ttNpEs'    : Global title translation based on
                          translation type, numbering plan
                          value and Encoding Scheme Value.

            'ttNpNaiEs' : Global title translation based on
                          translation type, numbering plan,
                          value, nature of address indicator
                          and encoding scheme value."

        SYNTAX INTEGER {
                nai(1),
                tt(2),
                ttNpEs(3),
                ttNpNaiEs(4)
        }

CItpTcGlobalTitleSelectorName ::= TEXTUAL-CONVENTION
        STATUS          current
        DESCRIPTION
                "The configured name associated with SCCP GTT
                 Selector.

                 An octet string specified by an administrator that
                 must be in human-readable form.  The names must
                 conform to the allowed characters that can be
                 specified via Command Line Interface(CLI).  The
                 names cannot contain control character and should
                 not contain leading or trailing white space."
        SYNTAX OCTET STRING ( SIZE ( 1..9  ) )

CItpTcGtaAddr    ::= TEXTUAL-CONVENTION
        STATUS          deprecated -- superceded by CItpTcGtaLongAddr
        DESCRIPTION
                "The configured digits in the SCCP GTT
                 Global Title Address.

                 An octet string specified by an administrator
                 must be in human-readable form.  The names must
                 conform to the allowed characters that can be
                 specified via Command Line Interface(CLI).  The
                 names cannot contain control character and should
                 not contain leading or trailing white space."
        SYNTAX OCTET STRING ( SIZE ( 8 ) )

CItpTcGtaLongAddr  ::= TEXTUAL-CONVENTION
        STATUS          current
        DESCRIPTION
                "The configured hexadecimal digits in the SCCP GTT
                 Global Title Address."
        SYNTAX OCTET STRING ( SIZE ( 0..64 ) )

CItpTcGtaDisplay ::= TEXTUAL-CONVENTION
        STATUS          deprecated
        DESCRIPTION
                "The configured digits in the SCCP GTT
                 Global Title Address. It consists of ASCII
                 representation of GTA hex digits.

                 This textual convention has been deprecated and
                 replaced by CItpTcGtaDisplayZB."
        SYNTAX OCTET STRING ( SIZE ( 1..15 ) )

CItpTcGtaDisplayZB ::= TEXTUAL-CONVENTION
        STATUS       deprecated -- superceded by CItpTcGtaLongDisplay
        DESCRIPTION
                "The configured digits in the SCCP GTT
                 Global Title Address. It consists of ASCII
                 representation of GTA hex digits."
        SYNTAX OCTET STRING ( SIZE ( 0..15 ) )

CItpTcGtaLongDisplay ::= TEXTUAL-CONVENTION
        STATUS       current
        DESCRIPTION
                "The configured digits in the SCCP GTT
                 Global Title Address. It consists of ASCII
                 representation of GTA hex digits."
        SYNTAX OCTET STRING ( SIZE ( 0..64 ) )

CItpTcGtaDisplayLen ::= TEXTUAL-CONVENTION
        STATUS          current
        DESCRIPTION
                "The SCCP GTT Global Title Address length."
        SYNTAX Unsigned32 ( 1..15 )

CItpTcGtaLongDisplayLen ::= TEXTUAL-CONVENTION
        STATUS          current
        DESCRIPTION
                "The SCCP GTT Global Title Address length."
        SYNTAX Unsigned32 ( 0..64 )

CItpTcNetworkName ::= TEXTUAL-CONVENTION
        STATUS          current
        DESCRIPTION
            "The network name is used to indicate the network
             in which this signalling point is participating.
             One or more instances of signalling points can
             exist in the same physical device.  This identifier
             will be used to correlate instances of signalling
             points by network.

             When multiple instance support is not enable the
             network name will default to the null string.

             An octet string specified by an administrator that
             must be in human-readable form.  The names must conform
             to the allowed characters that can be specified via
             Command Line Interface(CLI).  The names cannot contain
             control character and should not contain leading or
             trailing white space."
        SYNTAX OCTET STRING ( SIZE ( 0..19 ) )

CItpTcInstanceNumber ::= TEXTUAL-CONVENTION
        STATUS          current
        DESCRIPTION
                "The instance number used to select a particular
                 Signalling point."
        SYNTAX Unsigned32 ( 0..255 )

CItpTcLinksetId ::= TEXTUAL-CONVENTION
        STATUS          current
        DESCRIPTION
            "The configured name associated with an Signalling
             Point Linkset.

             An octet string specified by an administrator that must
             be in human-readable form.  The names must conform to
             the allowed characters that can be specified via
             Command Line Interface(CLI).  The names cannot contain
             control character and should not contain leading or
             trailing white space."
        SYNTAX OCTET STRING ( SIZE ( 1..19 ) )

CItpTcLinkSLC ::= TEXTUAL-CONVENTION
        STATUS          current
        DESCRIPTION
            "The Signalling Link Code. This is the link identifier
             within a linkset."
        SYNTAX Unsigned32 ( 0..15 )

CItpTcLinkType ::= TEXTUAL-CONVENTION
        STATUS          current
        DESCRIPTION
           "The link types.
            'other'  : This link is of some type not listed below.
            'serial' : This link is a serial link transporting
                         SS7 traffic.
            'sctpIp' : This a SCTP/IP link transporting
                         SS7 traffic.
            'hsl'    : This link is a high speed link using the ATM
                       protocol for transporting SS7 traffic.
            'virtual': This link is virtual link used to connect to
                       instance of signalling point running on the
                       same physical device.  The link will be used to
                       send and manage traffic between two signalling
                       acting as a gateway."
        SYNTAX INTEGER {
            other(1),
            serial(2),
            sctpIp(3),
            hsl(4),
            virtual(5)
        }

CItpTcNAI ::= TEXTUAL-CONVENTION
        STATUS          current
        DESCRIPTION
           "The SCCP GTT Network Address Indicator (NAI).
            The following values are generally used:
              Unknown Nature of Address (0),
              Subscriber Number (1),
              Reserved for national use (2),
              National Significant Number (3),
              International Number (4),
              Maximum NAI (127),
              Invalid NAI (253),
              Wild    NAI (254)."
        SYNTAX Integer32 (0..255)

CItpTcNetworkIndicator ::= TEXTUAL-CONVENTION
        STATUS          current
        DESCRIPTION
           "Network Indicator:
             international - International network
             national      - National network
             reserved      - Reserved for national use
             spare         - Spare (for international use only)
            'international'      : International network
            'internationalSpare' : International network spare
            'national'           : National network
            'nationalSpare'      : National network Spare"

        SYNTAX INTEGER {
            international(0),
            internationatSpare(1),
            national(2),
            nationalSpare(3)
        }

CItpTcNumberingPlan ::= TEXTUAL-CONVENTION
        STATUS          current
        DESCRIPTION
           "The SCCP GTT Numbering Plan (NP).
            The following values are generally used:
              Unknown NP (0),
              ISDN/Telephony NP (1),
              Spare    (2),
              Data  NP (3),
              Telex NP (4),
              Maritime Mobile NP (5),
              Land Mobile     NP (6),
              ISDN/Mobile     NP (7),
              Private NP (8).
              Max     NP (15),
              Invalid NP (253),
              Wild    NP (254)."
        SYNTAX Integer32 (0..255)

CItpTcPointCode ::= TEXTUAL-CONVENTION
        STATUS          current
        DESCRIPTION
           "The SS7 network node address as specified in the
            following references.  The format of the Point
            code depends on the variant defined in the
            CgspSS7Variant object as follows.

                   33222222222211111111110000000000
                   10987654321098765432109876543210
            ANSI:          nnnnnnnn                 - Network
                                   cccccccc         - Cluster
                                           mmmmmmmm - Member
            ITU:                     zzz            - Zone
                                        aaaaaaaa    - Area/Network
                                                iii - Identifier
            NTT:                   zzzzz            - Zone
                                        aaaa        - Area/Network
                                            iiiiiii - Identifier
            TTC:                   zzzzz            - Zone
                                        aaaa        - Area/Network
                                            iiiiiii - Identifier

            Note: The China variant has the same format as ANSI.

            This form of the point-code is not intended for
            for presentation."

        REFERENCE
            "The SS7 network node address as specified in the
             International Telecommunication Union standard Q.708:
             Specifications of Signalling System No. 7 - Numbering
             of International Signalling Point Codes, and by ANSI
             T1.111.8 Numbering of Signalling Point Codes.

             GF 001-9001 - Technical Specifications of Signalling
             System No. 7 for National Telephone Network of China."
        SYNTAX Unsigned32 ( 0..16777216)

CItpTcPointCodeMask ::= TEXTUAL-CONVENTION
        STATUS          current
        DESCRIPTION
           "A mask used to perform different operations on
            pointcodes."

        REFERENCE
            "The SS7 network node address as specified in the
             International Telecommunication Union standard Q.708:
             Specifications of Signalling System No. 7 - Numbering
             of International Signalling Point Codes, and by ANSI
             T1.111.8 Numbering of Signalling Point Codes."
        SYNTAX Unsigned32 ( 0..16777216)

CItpTcPointCodeType ::= TEXTUAL-CONVENTION
        STATUS          current
        DESCRIPTION
              "List of the possible Point Code types.
                'primary'     : The primary point used to communicate
                                information on the Signalling point.
                'additional'  : Additional point codes.
                'capability'  : capability point codes.
                'xua'         : MTP3-User Adaptation point codes or
                                SCCP-User Adaptation point codes."

        SYNTAX INTEGER {
                primary(1),
                additional(2),
                capability(3),
                xua(4)
        }

CItpTcQos ::= TEXTUAL-CONVENTION
        STATUS          current
        DESCRIPTION
            "The quality of service classification to be assigned
             to the IP packets used to transport the SS7 messages.
             The value can be from one to seven when selecting
             a Qos class or 255 to indicate the packet will not
             be assigned a Qos class. This value will be set to
             zero when cItpSpLinkType indicates that
             Quality of Service does not apply to this link."
        SYNTAX Unsigned32 (0..7 | 255)

CItpTcRouteTableName ::= TEXTUAL-CONVENTION
        STATUS          current
        DESCRIPTION
            "The configured name associated with an SP Route
             Table.

             An octet string specified by an administrator that must
             be in human-readable form.  The names must conform to
             the allowed characters that can be specified via
             Command Line Interface(CLI).  The names cannot contain
             control character and should not contain leading or
             trailing white space."
        SYNTAX OCTET STRING ( SIZE (1..19) )

CItpTcServiceIndicator ::= TEXTUAL-CONVENTION
        STATUS          current
        DESCRIPTION
           "The list of possible Service Indicator values. This
            identifies the type of SS7 packet.

            The service indicator codes for the international
            Signalling network are allocated as follows:

            'SNMM'        : Signalling network management
                            messages (SNMM)
            'SNTM'        : Signalling network testing and
                            maintenance messages (SNTM)
            'Spare2'      : Spare 2
            'SCCP'        : SCCP
            'TUP'         : Telephone User Part (TUP)
            'ISUP'        : ISDN User Part      (ISUP)
            'DUPC'        : Data User Part, call and circuit-related
                            messages (DUPC)
            'DUPF'        : Data User Part, facility registration and
                            cancellation messages (DUPF)
            'MTUP'        : Reserved for MTP Testing User Part (MTUP)
            'BISUP'       : Broadband ISDN User Part  (BISUP)
            'SISUP'       : Satellite ISDN User Part (SISUP)
            'Spare11'     : Spare 11
            'Spare12'     : Spare 12
            'Spare13'     : Spare 13
            'Spare14'     : Spare 14
            'Spare15'     : Spare 15"
        REFERENCE
           "ITU Q.704 Signalling network functions and messages section
            14.2.1 Service indicator."
        SYNTAX INTEGER {
            snmm(0),
            sntm(1),
            spare2(2),
            sccp(3),
            tup(4),
            isup(5),
            dupc(6),
            dupf(7),
            mtup(8),
            bisup(9),
            sisup(10),
            spare11(11),
            spare12(12),
            spare13(13),
            spare14(14),
            spare15(15)
        }

CItpTcSls ::= TEXTUAL-CONVENTION
        STATUS          current
        DESCRIPTION
            "The Signalling Link Selector is a numeric value that
             contains the MTP3 packets to allow load balancing of
             traffic across a link within a linkset or combined linkset.
             Each linkset provides one or more tables used to map
             Signalling Link Selectors to Signalling Link Codes.  The
             number of Signalling Link Selectors is 16 for ITU and 256
             for ANSI."
        SYNTAX Unsigned32 (0..255)

CItpTcSs7Variant ::= TEXTUAL-CONVENTION
        STATUS          current
        DESCRIPTION
            "The list of SS7 variants.
            'ANSI'    : The ANSI variant of the SS7 specification.
            'ITU'     : The ITU variant of the SS7 specification.
            'China'   : The China national variant. This variant
                        is a combination of ITU and ANSI. The
                        protocol matches ITU except where the
                        point-code has been expanded to ANSI format."
        REFERENCE
            "GF 001-9001 - Technical Specifications of Signalling
             System No. 7 for National Telephone Network of China."
        SYNTAX INTEGER {
            ansi(1),
            itu(2),
            china(3)
    }


CItpTcSubSystemNumber ::= TEXTUAL-CONVENTION
        STATUS          current
        DESCRIPTION
            "The SCCP Subsystem Number .  A  value of zero
             indicates that a subsystem is not specified."
        SYNTAX Unsigned32 (0 | 2..255 )

CItpTcSubSystemNumberMask ::= TEXTUAL-CONVENTION
        STATUS          current
        DESCRIPTION
                "The SCCP Subsystem Number Mask."
        SYNTAX Unsigned32 ( 2..255 )

CItpTcTableLoadStatus ::= TEXTUAL-CONVENTION
        STATUS          current
        DESCRIPTION
            "The status of the current or prior load operation.
             'loadNotRequested' : load operations have not been
                                  requested.

             'loadInProgress'  : load request is active.

             'loadComplete' : load request complete without errors.

             'loadCompleteWithErrors' : Load request completed with
                                        some type of errors that
                                        prevented the adding of one
                                        or more entries.

             'loadFailed' : Load request failed."

        SYNTAX INTEGER {
            loadNotRequested(1),
            loadInProgress(2),
            loadComplete(3),
            loadCompleteWithErrors(4),
            loadFailed(5)
        }

CItpTcTimerMtp2T01 ::= TEXTUAL-CONVENTION
        STATUS          current
        DESCRIPTION
           "Alignment ready timer. The default and valid range is
            dependant on the value of variant.

                  Min      Max      Def
                  ------   ------   ------
            ANSI   12500    16000    13000
            ITU    40000    50000    40000

            The SYNTAX statement allows values for both
            the ANSI, ITU variants and MTP2 Peer-to-Peer
            Adaptation Layer."
        REFERENCE
           "ITU Q.703 Signalling Link.
            ANSI T1.111.3 Telecommunications - Signalling system
            No. 7 (SS7)-Message Transfer Part (MTP)."
        SYNTAX  Unsigned32 (5000..150000)


CItpTcTimerMtp2T02 ::= TEXTUAL-CONVENTION
        STATUS          current
        DESCRIPTION
           "Not aligned timer. The default and valid range is
            dependant on the value of variant.

            This timer is only applicable if cItpTcLinkType
            is serial. A get on this object will return a
            zero if the link is not serial.

                  Min      Max      Def
                  ------   ------   ------
            ANSI    5000    14000    11500
            ITU     5000   150000     5000

            The SYNTAX statement allows values for both
            the ANSI and ITU variants."

        REFERENCE
           "ITU Q.703 Signalling Link.
            ANSI T1.111.3 Telecommunications - Signalling system
            No. 7 (SS7)-Message Transfer Part (MTP)."

        SYNTAX  Unsigned32 (0 | 5000..150000)

CItpTcTimerMtp2T03 ::= TEXTUAL-CONVENTION
        STATUS          current
        DESCRIPTION
           "Aligned timer. The default and valid range is
            dependant on the value of variant.

            This timer is only applicable if cItpTcLinkType
            is serial. A get on this object will return a
            zero if the link is not serial.

                  Min      Max      Def
                  ------   ------   ------
            ANSI    5000    14000    11500
            ITU     1000     2000     1500

            The SYNTAX statement allows values for both
            the ANSI and ITU variants. "
        REFERENCE
           "ITU Q.703 Signalling Link.
            ANSI T1.111.3 Telecommunications - Signalling system
            No. 7 (SS7)-Message Transfer Part (MTP)."

        SYNTAX  Unsigned32 (0 | 1000..14000)

CItpTcTimerMtp2T04E ::= TEXTUAL-CONVENTION
        STATUS          current
        DESCRIPTION
           "Proving period timer emergency timer. The default and
            valid range is dependant on the value of
            variant.

            This timer is only applicable if cItpTcLinkType
            is serial. A get on this object will return a
            zero if the link is not serial.

                  Min      Max      Def
                  ------   ------   ------
            ANSI     540      660      600
            ITU      400      600      500

            The SYNTAX statement allows values for both
            the ANSI and ITU variants. "
        REFERENCE
            "ITU Q.703 Signalling Link.
            ANSI T1.111.3 Telecommunications - Signalling system
            No. 7 (SS7)-Message Transfer Part (MTP)."

        SYNTAX  Unsigned32 (0 | 400..660)

CItpTcTimerMtp2T04N ::= TEXTUAL-CONVENTION
        STATUS          current
        DESCRIPTION
           "Proving period timer normal timer. The default and
            valid range is dependant on the value of
            variant.

            This timer is only applicable if cItpTcLinkType
            is serial. A get on this object will return a
            zero if the link is not serial.

                  Min      Max      Def
                  ------   ------   ------
            ANSI    2007     2530     2300
            ITU     7500     9500     8200

            The SYNTAX statement allows values for both
            the ANSI and ITU variants. "
        REFERENCE
           "ITU Q.703 Signalling Link.
            ANSI T1.111.3 Telecommunications - Signalling system
            No. 7 (SS7)-Message Transfer Part (MTP)."

        SYNTAX  Unsigned32 (0 | 2007..9500)

CItpTcTimerMtp2T05 ::= TEXTUAL-CONVENTION
        STATUS          current
        DESCRIPTION
           "Sending SIB timer. The default and valid range is
            dependant on the value of variant.

            This timer is only applicable if cItpTcLinkType
            is serial. A get on this object will return a
            zero if the link is not serial.

                  Min      Max      Def
                  ------   ------   ------
            ANSI      80      120       80
            ITU       80      120      100

            The SYNTAX statement allows values for both
            the ANSI and ITU variants. "
        REFERENCE
            "ITU Q.703 Signalling Link.
            ANSI T1.111.3 Telecommunications - Signalling system
            No. 7 (SS7)-Message Transfer Part (MTP)."

        SYNTAX  Unsigned32 (0 | 80..120)

CItpTcTimerMtp2T06 ::= TEXTUAL-CONVENTION
        STATUS          current
        DESCRIPTION
           "Remote congestion timer. The default and valid range is
            dependant on the value of variant.

                  Min      Max      Def
                  ------   ------   ------
            ANSI    1000     6000     1000
            ITU     3000     6000     3000

            The SYNTAX statement allows values for both
            the ANSI, ITU variants and MTP2 Peer-to-Peer
            Adaptation Layer."
        REFERENCE
            "ITU Q.703 Signalling Link.
            ANSI T1.111.3 Telecommunications - Signalling system
            No. 7 (SS7)-Message Transfer Part (MTP)."
        SYNTAX  Unsigned32 ( 1000..6000 )

CItpTcTimerMtp2T07 ::= TEXTUAL-CONVENTION
        STATUS          current
        DESCRIPTION
            "Excessive delay of acknowledgement timer. The default
             and valid range is dependant on the value of
             variant().

             This timer is only applicable if cItpTcLinkType
             is serial. A get on this object will return a
             zero if the link is not serial.

                  Min      Max      Def
                  ------   ------   ------
            ANSI     500     2000     1000
            ITU      500     2000     1000

            The SYNTAX statement allows values for both
            the ANSI and ITU variants."
        REFERENCE
            "ITU Q.703 Signalling Link.
            ANSI T1.111.3 Telecommunications - Signalling system
            No. 7 (SS7)-Message Transfer Part (MTP)."

        SYNTAX  Unsigned32 (0 | 100..6000)

CItpTcTimerMtp3T01 ::= TEXTUAL-CONVENTION
        STATUS          current
        DESCRIPTION
            "Delay to avoid message mis-sequencing on changeover.
             Ranges by variant.

                   Min      Max      Def
                   ------   ------   ------
             ANSI     500     1200      800
             ITU      500     1200      800

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (500..1200)

CItpTcTimerMtp3T02 ::= TEXTUAL-CONVENTION
        STATUS          current
        DESCRIPTION
            "Waiting for changeover acknowledgement.
             Ranges by variant.

                   Min      Max      Def
                   ------   ------   ------
             ANSI     700     2000     1400
             ITU      700     2000     1400

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (700..2000)

CItpTcTimerMtp3T03 ::= TEXTUAL-CONVENTION
        STATUS          current
        DESCRIPTION
            "Time controlled diversion-delay to avoid
            mis-sequencing on change back.
             Ranges by variant.

                   Min      Max      Def
                   ------   ------   ------
             ANSI     500     1200      800
             ITU      500     1200      800

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (500..1200)

CItpTcTimerMtp3T04 ::= TEXTUAL-CONVENTION
        STATUS          current
        DESCRIPTION
            "Waiting for change back acknowledgement (first
            attempt).
             Ranges by variant.

                   Min      Max      Def
                   ------   ------   ------
             ANSI     500     1200      800
             ITU      500     1200      800

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (500..1200)

CItpTcTimerMtp3T05 ::= TEXTUAL-CONVENTION
        STATUS          current
        DESCRIPTION
            "Waiting for change back acknowledgement (second
             attempt).
             Ranges by variant.

                   Min      Max      Def
                   ------   ------   ------
             ANSI     500     1200      800
             ITU      500     1200      800

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (500..1200)

CItpTcTimerMtp3T06 ::= TEXTUAL-CONVENTION
        STATUS          current
        DESCRIPTION
            "Delay to avoid message mis-sequencing on controlled
             rerouting.
             Ranges by variant.

                   Min      Max      Def
                   ------   ------   ------
             ANSI     500     1200      800
             ITU      500     1200      800

             The SYNTAX statement allows values for both
             the ANSI and ITU variants. "
        REFERENCE
            "ITU Q.704 Signalling network functions and messages.
            ANSI T1.111 Telecommunications - Signalling system
            No. 7 (SS7)-Message Transfer Part (MTP)."
        SYNTAX  Unsigned32 (500..1200)

CItpTcTimerMtp3T07 ::= TEXTUAL-CONVENTION
        STATUS          current
        DESCRIPTION
            "Waiting for Signalling data link connection
             acknowledgement.
             Ranges by variant.

                   Min      Max      Def
                   ------   ------   ------
             ANSI    1000     2000     1500
             ITU     1000     2000     1500

             The SYNTAX statement allows values for both
             the ANSI and ITU variants. A value of zero
             indicates a value is not defined for a particular
             variant or is not supported by the implementation."

        REFERENCE
            "ITU Q.704 Signalling network functions and messages.
             ANSI T1.111 Telecommunications - Signalling system
             No. 7 (SS7)-Message Transfer Part (MTP)."
        SYNTAX  Unsigned32 (0 | 1000..2000)

CItpTcTimerMtp3T08 ::= TEXTUAL-CONVENTION
        STATUS          current
        DESCRIPTION
            "Transfer prohibited inhibition timer (transient
             solution).
             Ranges by variant.

                   Min      Max      Def
                   ------   ------   ------
             ANSI     800     1200     1000
             ITU      800     1200     1000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (800..1200)

CItpTcTimerMtp3T10 ::= TEXTUAL-CONVENTION
        STATUS          current
        DESCRIPTION
            "Waiting to repeat Signalling routeset test message.
             Ranges by variant.

                   Min      Max      Def
                   ------   ------   ------
             ANSI   30000    60000    45000
             ITU    30000    60000    45000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (30000..60000)

CItpTcTimerMtp3T11 ::= TEXTUAL-CONVENTION
        STATUS          current
        DESCRIPTION
            "Transfer restricted timer. (This is one way of
             implementing the function described in 13.4/Q.704 and
             mainly intended to simplify SPs.).
             Ranges by variant.

                   Min      Max      Def
                   ------   ------   ------
             ANSI   30000    90000    60000
             ITU    30000    90000    60000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (30000..90000)

CItpTcTimerMtp3T12 ::= TEXTUAL-CONVENTION
        STATUS          current
        DESCRIPTION
            "Waiting for uninhibit acknowledgement.
             Ranges by variant.

                   Min      Max      Def
                   ------   ------   ------
             ANSI     800     1500     1150
             ITU      800     1500     1150

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (800..1500)

CItpTcTimerMtp3T13 ::= TEXTUAL-CONVENTION
        STATUS          current
        DESCRIPTION
            "Waiting for force uninhibit.
             Ranges by variant.

                   Min      Max      Def
                   ------   ------   ------
             ANSI     800     1500     1150
             ITU      800     1500     1150

             The SYNTAX statement allows values for both
             the ANSI and ITU variants. "
        REFERENCE
            "ITU Q.704 Signalling network functions and messages.
             ANSI T1.111 Telecommunications - Signalling system
            No. 7 (SS7)-Message Transfer Part (MTP)."
        SYNTAX  Unsigned32 (800..1500)

CItpTcTimerMtp3T14 ::= TEXTUAL-CONVENTION
        STATUS          current
        DESCRIPTION
            "Waiting for inhibition acknowledgement.
             Ranges by variant.

                   Min      Max      Def
                   ------   ------   ------
             ANSI    2000     3000     2500
             ITU     2000     3000     2500

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (2000..3000)

CItpTcTimerMtp3T15 ::= TEXTUAL-CONVENTION
        STATUS          current
        DESCRIPTION
            "Waiting to start Signalling routeset congestion
             test. Ranges by variant.

                   Min      Max      Def
                   ------   ------   ------
             ANSI    2000     3000     2500
             ITU     2000     3000     2500

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (2000..3000)

CItpTcTimerMtp3T16 ::= TEXTUAL-CONVENTION
        STATUS          current
        DESCRIPTION
            "Waiting for routeset congestion status update.
             Ranges by variant.

                   Min      Max      Def
                   ------   ------   ------
             ANSI    1400     2000     1700
             ITU     1400     2000     1700

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (1400..2000)

CItpTcTimerMtp3T17 ::= TEXTUAL-CONVENTION
        STATUS          current
        DESCRIPTION
            "Delay to avoid oscillation of initial alignment
             failure and link restart.
             Ranges by variant.

                   Min      Max      Def
                   ------   ------   ------
             ANSI     800     1500     1150
             ITU      800     1500     1150

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (800..1500)

CItpTcTimerMtp3T18 ::= TEXTUAL-CONVENTION
        STATUS          current
        DESCRIPTION
            "This timers servers different function based on the
             variant.

             ANSI: Repeat TFR once by response method
             ITU:  MTP restart link supervision

                   Min      Max      Def
                   ------   ------   ------
             ANSI    2000    20000    11000
             ITU     1000    31000    30000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (1000..31000)

CItpTcTimerMtp3T19 ::= TEXTUAL-CONVENTION
        STATUS          current
        DESCRIPTION
            "This timers servers different function based on the
             variant.

             ANSI: failed craft timer referral timer
             ITU:  supervision timer during MTP restart

                   Min      Max      Def
                   ------   ------   ------
             ANSI  480000   600000   540000
             ITU    67000    69000    68000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (67000..600000)

CItpTcTimerMtp3T20 ::= TEXTUAL-CONVENTION
        STATUS          current
        DESCRIPTION
            "This timers servers different function based on the
             variant.

             ANSI: waiting to repeat local inhibit test
             ITU:  MTP restart timer at the Signalling point

                   Min      Max      Def
                   ------   ------   ------
             ANSI   90000   120000   105000
             ITU     1000    61000    60000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (1000..120000)

CItpTcTimerMtp3T21 ::= TEXTUAL-CONVENTION
        STATUS          current
        DESCRIPTION
            "This timers servers different function based on the
             variant.

             ANSI: waiting to repeat remote inhibit test)
             ITU:  MTP restart timer at adjacent Signalling point

                   Min      Max      Def
                   ------   ------   ------
             ANSI   90000   120000   105000
             ITU    63000    65000    64000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (63000..120000)

CItpTcTimerMtp3T22 ::= TEXTUAL-CONVENTION
        STATUS          current
        DESCRIPTION
            "This timers servers different function based on the
             variant.

             ANSI: restarting SP waiting for Signalling links avail
             ITU:  local inhibit test timer

                   Min      Max      Def
                   ------   ------   ------
             ANSI   36000    60000    30000
             ITU    80000   360000   300000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (36000..360000)

CItpTcTimerMtp3T23 ::= TEXTUAL-CONVENTION
        STATUS          current
        DESCRIPTION
            "This timers servers different function based on the
             variant.

             ANSI: restarting SP waiting to receive all TRA msgs
             ITU:  remote inhibit test timer

                   Min      Max      Def
                   ------   ------   ------
             ANSI    9000    60000    30000
             ITU    80000   360000   300000

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (9000..360000)

CItpTcTimerMtp3T24 ::= TEXTUAL-CONVENTION
        STATUS          current
        DESCRIPTION
            "This timers servers different function based on the
             variant.

             ANSI: restarting SP waiting to broadcast all TRA msgs
             ITU:  stabilizing timer after local processor outage

                   Min      Max      Def
                   ------   ------   ------
             ANSI    9000    60000    30000
             ITU      500      500      500

             The SYNTAX statement allows values for both
             the ANSI and ITU variants. "
        REFERENCE
            "ITU Q.704 Signalling network functions and messages.
             ANSI T1.111 Telecommunications - Signalling system
             No. 7 (SS7)-Message Transfer Part (MTP)."
        SYNTAX  Unsigned32 (500..60000)

CItpTcTimerMtp3T25 ::= TEXTUAL-CONVENTION
        STATUS          current
        DESCRIPTION
           "Timer at Signalling Point (SP) adjacent to restarting
            SP, waiting for traffic restart allowed message.
             Ranges by variant.

                   Min      Max      Def
                   ------   ------   ------
             ANSI   30000    35000    30000

             This timer is not used when the variant is ITU.
             A value of zero indicates a value is not defined
             for a particular variant or is not supported by the
             implementation."
        REFERENCE
            "ANSI T1.111 Telecommunications - Signalling system
             No. 7 (SS7)-Message Transfer Part (MTP)"
        SYNTAX  Unsigned32 (0 | 30000..35000)

CItpTcTimerMtp3T26 ::= TEXTUAL-CONVENTION
        STATUS          current
        DESCRIPTION
           "Timer at restarting SP waiting to repeat traffic
            restart waiting message.
             Ranges by variant.

                   Min      Max      Def
                   ------   ------   ------
             ANSI   12000    15000    12000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 12000..15000)

CItpTcTimerMtp3T27 ::= TEXTUAL-CONVENTION
        STATUS          current
        DESCRIPTION
            "Minimum duration of unavailability for full restart.
             Ranges by variant.

                   Min      Max      Def
                   ------   ------   ------
             ANSI    2000    50000     4000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 2000..50000)

CItpTcTimerMtp3T28 ::= TEXTUAL-CONVENTION
        STATUS          current
        DESCRIPTION
            "Timer at SP adjacent to restarting SP waiting for
            traffic restart waiting message.
             Ranges by variant.

                   Min      Max      Def
                   ------   ------   ------
             ANSI    3000    35000    30000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 3000..35000)

CItpTcTimerMtp3T29 ::= TEXTUAL-CONVENTION
        STATUS          current
        DESCRIPTION
            "Timer started when TRA sent in response to unexpected
             TRA or TRW.
             Ranges by variant.

                   Min      Max      Def
                   ------   ------   ------
             ANSI   60000    65000    63000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 60000..65000)

CItpTcTimerMtp3T30 ::= TEXTUAL-CONVENTION
        STATUS          current
        DESCRIPTION
            "Timer to limit sending of TFPs and TFRs in response
             to unexpected TRA or TRW.
             Ranges by variant.

                   Min      Max      Def
                   ------   ------   ------
             ANSI   30000    35000    33000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 30000..35000)

CItpTcTimerMtp3T31 ::= TEXTUAL-CONVENTION
        STATUS          current
        DESCRIPTION
            "False link congestion detection timer.
             Ranges by variant.

                   Min      Max      Def
                   ------   ------   ------
             ANSI   10000   120000    60000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 10000..120000)

CItpTcTimerMtp3T32 ::= TEXTUAL-CONVENTION
        STATUS          current
        DESCRIPTION
            "Link oscillation timer - Procedure A.
             Ranges by variant.

                   Min      Max      Def
                   ------   ------   ------
             ANSI    5000   120000    60000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 5000..120000)

CItpTcTimerMtp3T33 ::= TEXTUAL-CONVENTION
        STATUS          current
        DESCRIPTION
            "Probation timer for link oscillation - Procedure B.
             Ranges by variant.

                   Min      Max      Def
                   ------   ------   ------
             ANSI   60000   600000   300000

             This timer is not used when the variant is ITU.
             A value of zero indicates a value is not defined
             for a particular variant or is not supported by
             the implementation."
        REFERENCE
            "ANSI T1.111 Telecommunications - Signalling system
             No. 7 (SS7)-Message Transfer Part (MTP)"
        SYNTAX  Unsigned32 (0 | 60000..600000)

CItpTcTimerMtp3T34 ::= TEXTUAL-CONVENTION
        STATUS          current
        DESCRIPTION
            "Suspension timer for link oscillation - Procedure B.
             Ranges by variant.

                   Min      Max      Def
                   ------   ------   ------
             ANSI    5000   120000    60000

             This timer is not used when the variant is ITU.
             A value of zero indicates a value is not defined
             for a particular variant or is not supported by
             the implementation."
        REFERENCE
            "ANSI T1.111 Telecommunications - Signalling system
            No. 7 (SS7)-Message Transfer Part (MTP)"
        SYNTAX  Unsigned32 (0 | 5000..120000)

CItpTcTimerLinkTest ::= TEXTUAL-CONVENTION
        STATUS          current
        DESCRIPTION
            "Signalling Link test acknowledgement timer.

                    Min      Max      Def
                   ------   ------   ------
             ANSI    4000    12000     8000

             This timer is not used when the variant is ITU.
             A value of zero indicates a value is not defined
             for a particular variant or is not supported by
             the implementation."
        REFERENCE
            "ITU Q.704 Signalling network functions and messages.
             ANSI T1.111 Telecommunications - Signalling system
             No. 7 (SS7)-Message Transfer Part (MTP)."
        SYNTAX  Unsigned32 (0 | 4000..12000)

CItpTcTimerLinkMessage ::= TEXTUAL-CONVENTION
        STATUS          current
        DESCRIPTION
            "Interval timer for sending test messages.

                   Min      Max      Def
                   ------   ------   ------
             ANSI   30000    90000    60000

             This timer is not used when the variant is ITU.
             A value of zero indicates a value is not defined
             for a particular variant or is not supported by
             the implementation."
        REFERENCE
            "ITU Q.704 Signalling network functions and messages.
             ANSI T1.111 Telecommunications - Signalling system
             No. 7 (SS7)-Message Transfer Part (MTP)."
        SYNTAX  Unsigned32 (0 | 30000..90000)

CItpTcTimerLinkActRetry ::= TEXTUAL-CONVENTION
        STATUS          current
        DESCRIPTION
            "Link activation retry timer.

                   Min      Max      Def
                   ------   ------   ------
             ANSI   60000    90000    60000

             This timer is not used when the variant is ITU.
             A value of zero indicates a value is not defined
             for a particular variant or is not supported by
             the implementation."
        REFERENCE
            "ITU Q.704 Signalling network functions and messages.
             ANSI T1.111 Telecommunications - Signalling system
             No. 7 (SS7)-Message Transfer Part (MTP)."
        SYNTAX  Unsigned32 (0 | 60000..90000)

CItpTcTranslationType ::= TEXTUAL-CONVENTION
        STATUS          current
        DESCRIPTION
           "The Translation Type for SCCP GTT GTA specifies Title
            Translation or Subsystem Number (SSN)
           'tt'  : The GTT GTA has specified Title Translation
           'ssn' : The GTT GTA has specified Subsystem Number."
        SYNTAX INTEGER {
                tt(1),
                ssn(2)
        }

CItpTcURL ::= TEXTUAL-CONVENTION
        STATUS          current
        DESCRIPTION
            "The URL used to load a configuration file.

             An octet string specified by an administrator that must
             be in human-readable form.  The names must conform to
             the allowed characters that can be specified via
             Command Line Interface(CLI).  The names cannot contain
             control character and should not contain leading or
             trailing white space."
        SYNTAX OCTET STRING ( SIZE (0..255) )

CItpTcXuaName ::= TEXTUAL-CONVENTION
        STATUS          current
        DESCRIPTION
                "The configured name associated with M3UA/SUA
                 ASP or AS name.

                 An octet string specified by an administrator that
                 must be in human-readable form.  The names must
                 conform to the allowed characters that can be
                 specified via Command Line Interface(CLI).  The
                 names cannot contain control character and should
                 not contain leading or trailing white space."
        SYNTAX OCTET STRING ( SIZE ( 0..12 ) )

END
