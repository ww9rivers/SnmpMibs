-- *****************************************************************
-- CISCO-NOTIFICATION-LOG-CAPABILITY.my,v 2.0 2005/11/29
--
-- AGENT-CAPABILITIES mib for NOTIFICATION-LOG-MIB
--
-- Nov 2005, Anirban Karmakar
--
-- Copyright(c) 2005-2008 by Cisco Systems Inc.
--
-- ***************************************************************

CISCO-NOTIFICATION-LOG-CAPABILITY DEFINITIONS ::= BEGIN

IMPORTS
    MODULE-IDENTITY
        FROM SNMPv2-SMI
    AGENT-CAPABILITIES
        FROM SNMPv2-CONF
    ciscoAgentCapability
        FROM CISCO-SMI;


ciscoNotificationLogCapability MODULE-IDENTITY
    LAST-UPDATED    "200812180000Z"
    ORGANIZATION    "Cisco Systems, Inc."
    CONTACT-INFO
            "Cisco Systems
            Customer Service

            Postal: 170 West Tasman Drive
            San Jose, CA  95134
            USA

            Tel: +1 800 553-NETS

            E-mail: cs-snmp@cisco.com"
    DESCRIPTION
        "Agent capabilities for NOTIFICATION-LOG-MIB"
    REVISION        "200812180000Z"
    DESCRIPTION
        "Added agent Capability for NX-OS 4.1(3)"
    REVISION        "200701220000Z"
    DESCRIPTION
        "Added agent Capability for IOS XR 3.4 on CRS-1"
    REVISION        "200511290000Z"
    DESCRIPTION
        "Added CAPABILITY macro for 12.2S."
    REVISION        "200511180000Z"
    DESCRIPTION
        "Initial version of this MIB module."
    ::= { ciscoAgentCapability 463 }



cNotificationLogCapabilityV12R04 AGENT-CAPABILITIES
    PRODUCT-RELEASE "Cisco IOS 12.4"
    STATUS          current
    DESCRIPTION
        "NOTIFICATION-LOG-MIB capabilities"

    SUPPORTS        NOTIFICATION-LOG-MIB
    INCLUDES        {
                        notificationLogConfigGroup,
                        notificationLogStatsGroup,
                        notificationLogLogGroup,
                        notificationLogDateGroup
                    }
    VARIATION       nlmConfigGlobalEntryLimit
    DESCRIPTION
        "The default value of this object is 0 as per RFC3014.
        This default value is too liberal for an IOS
        implementation. The implementation of this MIB supports
        the default value of this object as 500."

    VARIATION       nlmConfigGlobalAgeOut
    DESCRIPTION
        "The default value of this object is 24 hrs i.e.
        1440 minutes as per RFC3014. Tis default value is too
        liberal for an IOS implementation. The implementation of
        this MIB supports the default value of this object as
        15 minutes."

    VARIATION       nlmConfigLogEntryLimit
    DESCRIPTION
        "The default value of this object is 0 as per RFC3014.
        This default value is too liberal for an IOS
        implementation. The implementation of this MIB supports
        the default value of this object as 500."

    ::= { ciscoNotificationLogCapability 1 }

cNotificationLogCapabilityV12R2S AGENT-CAPABILITIES
    PRODUCT-RELEASE "Cisco IOS 12.2S and 12.2S based releases"
    STATUS          current
    DESCRIPTION
        "NOTIFICATION-LOG-MIB capabilities"

    SUPPORTS        NOTIFICATION-LOG-MIB
    INCLUDES        {
                        notificationLogConfigGroup,
                        notificationLogStatsGroup,
                        notificationLogLogGroup,
                        notificationLogDateGroup
                    }
    VARIATION       nlmConfigGlobalEntryLimit
    DESCRIPTION
        "The default value of this object is 0 as per RFC3014.
        This default value is too liberal for an IOS
        implementation. The implementation of this MIB supports
        the default value of this object as 500."

    VARIATION       nlmConfigGlobalAgeOut
    DESCRIPTION
        "The default value of this object is 24 hrs i.e.
        1440 minutes as per RFC3014. Tis default value is too
        liberal for an IOS implementation. The implementation of
        this MIB supports the default value of this object as
        15 minutes."

    VARIATION       nlmConfigLogEntryLimit
    DESCRIPTION
        "The default value of this object is 0 as per RFC3014.
        This default value is too liberal for an IOS
        implementation. The implementation of this MIB supports
        the default value of this object as 500."

    ::= { ciscoNotificationLogCapability 2 }

cNotificationLogCapIOSXRV3R4CRS1 AGENT-CAPABILITIES
    PRODUCT-RELEASE "Cisco IOS XR 3.4 for CRS-1"
    STATUS          current
    DESCRIPTION
        "NOTIFICATION-LOG-MIB capabilities"

    SUPPORTS        NOTIFICATION-LOG-MIB
    INCLUDES        {
                        notificationLogConfigGroup,
                        notificationLogStatsGroup,
                        notificationLogLogGroup,
                        notificationLogDateGroup
                    }
    VARIATION       nlmConfigGlobalEntryLimit
    DEFVAL          { 500 }
    DESCRIPTION
        "The default value of this object is 0 as per RFC3014.
        This default value is too liberal for an IOS XR
        implementation. The implementation of this MIB supports
        the default value of this object as 500."

    VARIATION       nlmConfigGlobalAgeOut
    DEFVAL          { 15 }
    DESCRIPTION
        "The default value of this object is 24 hrs i.e.
        1440 minutes as per RFC3014. Tis default value is too
        liberal for an IOS XR implementation. The implementation
        of this MIB supports the default value of this object as
        15 minutes."

    VARIATION       nlmConfigLogEntryLimit
    DEFVAL          { 500 }
    DESCRIPTION
        "The default value of this object is 0 as per RFC3014.
        This default value is too liberal for an IOS XR
        implementation. The implementation of this MIB supports
        the default value of this object as 500."

    VARIATION       nlmConfigLogEntryStatus
    ACCESS          read-only
    DESCRIPTION
        "SNMP SET is not supported"

    VARIATION       nlmLogEngineID
    ACCESS          read-only
    DESCRIPTION
        "Hard coded to NULL in present implementation because
        the log can contain Notifications from only one engine
        or the Trap is in SNMPv1 format."

    VARIATION       nlmLogContextEngineID
    DESCRIPTION
        "Hard coded to NULL in present implementation because
        the Notification was received in a protocol which
        has a contextEngineID element otherthan SNMPv3."

    VARIATION       nlmLogEngineTDomain
    ACCESS          not-implemented
    DESCRIPTION
        "Not supported in current implementaion."

    ::= { ciscoNotificationLogCapability 3 }

cNotificationLogCapNXOSV04R0103 AGENT-CAPABILITIES
    PRODUCT-RELEASE "Cisco NX-OS 4.1(3) on MDS9000 and Nexus7000 Storage Switches"
    STATUS          current
    DESCRIPTION
        "NOTIFICATION-LOG-MIB capabilities"

    SUPPORTS        NOTIFICATION-LOG-MIB
    INCLUDES        {
                        notificationLogConfigGroup,
                        notificationLogStatsGroup,
                        notificationLogLogGroup,
                        notificationLogDateGroup
                    }
    VARIATION       nlmConfigGlobalEntryLimit
    DEFVAL          { 25 }
    DESCRIPTION
        "The default value of this object is 0 as per RFC3014.
        This default value is too liberal for an NX-OS
        implementation. The implementation of this MIB supports
        the default value of this object as 25."

    VARIATION       nlmConfigGlobalAgeOut
    DEFVAL          { 5 }
    DESCRIPTION
        "The default value of this object is 24 hrs i.e.
        1440 minutes as per RFC3014. This default value is too
        liberal for an NX-OS implementation. The implementation
        of this MIB supports the default value of this object as
        5 minutes."

    ::= { ciscoNotificationLogCapability 4 }

END
