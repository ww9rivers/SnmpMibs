-- *****************************************************************
-- CISCO-SNMPv2-CAPABILITY.my: SNMPv2-MIB AGENT-CAPABILITIES
--
-- August   1994, Jeffrey T. Johnson
--
-- Copyright (c) 1994, 2002, 2004, 2006-2008 by cisco Systems Inc.
-- All rights reserved.
-- *****************************************************************

CISCO-SNMPv2-CAPABILITY DEFINITIONS ::= BEGIN

IMPORTS
    MODULE-IDENTITY
        FROM SNMPv2-SMI
    AGENT-CAPABILITIES
        FROM SNMPv2-CONF
    DisplayString
        FROM SNMPv2-TC
    ciscoAgentCapability
        FROM CISCO-SMI;


ciscoSnmpV2Capability MODULE-IDENTITY
    LAST-UPDATED    "200711120000Z"
    ORGANIZATION    "Cisco Systems, Inc."
    CONTACT-INFO
            "Cisco Systems
            Customer Service

            Postal: 170 West Tasman Drive
            San Jose, CA  95134
            USA

            Tel: +1 800 553-NETS

            E-mail: cs-snmp@cisco.com"
    DESCRIPTION
        "Agent capabilities for SNMPv2-MIB"
    REVISION        "200711120000Z"
    DESCRIPTION
        "Added capability statement
        ciscoSnmpV2Capc4710aceVA1R700 for ACE
        4710 Application Control Engine Appliance."
    REVISION        "200605300000Z"
    DESCRIPTION
        "Added capability statement
        ciscoSnmpV2CapACSWV03R000 for Application
        Control Engine (ACE).

        For ciscoSnmpV2CapabilityV10R02 commented
        out references to object groups
        snmpStatsGroup, snmpV1Group, snmpORGroup,
        snmpTrapGroup because they are defined only
        in the original RFC 1450, not in the latest
        RFC 3418."
    REVISION        "200604240000Z"
    DESCRIPTION
        "Added the VARIATION for the notification
        authenticationFailure in
        ciscoSnmpV2CapCatOSV08R0301.

        Added capability statement
        ciscoSnmpV2CapCatOSV08R0601."
    REVISION        "200403180000Z"
    DESCRIPTION
        "Added ciscoSnmpV2CapCatOSV08R0301."
    REVISION        "200202070000Z"
    DESCRIPTION
        "Added following agent capabilities:
        - ciscoMgxSnmpV2CapabilityV20 for
          MGX8850 series
        - ciscoBpxSesSnmpV2CapabilityV10 for
           BPX SES."
    REVISION        "200201310000Z"
    DESCRIPTION
        "Added 'ciscoRpmsSnmpV2CapabilityV20' for
        Cisco Resource Policy Management Server
        (RPMS) 2.0."
    REVISION        "199408180000Z"
    DESCRIPTION
        "Initial version of this MIB module."
    ::= { ciscoAgentCapability 113 }



ciscoSnmpV2CapabilityV10R02 AGENT-CAPABILITIES
    PRODUCT-RELEASE "Cisco IOS 10.2"
    STATUS          current
    DESCRIPTION
        "IOS 10.2 SNMPv2 MIB capabilities"

    SUPPORTS        SNMPv2-MIB
    INCLUDES        { snmpSetGroup }
    ::= { ciscoSnmpV2Capability 1 }

ciscoRpmsSnmpV2CapabilityV20 AGENT-CAPABILITIES
    PRODUCT-RELEASE "Cisco Resource Policy Management Server (RPMS) 2.0"
    STATUS          current
    DESCRIPTION
        "Cisco RPMS 2.0 SNMPv2 MIB capabilities."

    SUPPORTS        SNMPv2-MIB
    INCLUDES        {
                        snmpGroup,
                        snmpCommunityGroup,
                        snmpSetGroup,
                        systemGroup,
                        snmpBasicNotificationsGroup
                    }
    VARIATION       snmpInBadCommunityUses
    ACCESS          not-implemented
    DESCRIPTION
        "This object is not implemented."

    VARIATION       sysORLastChange
    ACCESS          not-implemented
    DESCRIPTION
        "This object is not implemented."

    VARIATION       sysORID
    ACCESS          not-implemented
    DESCRIPTION
        "This object is not implemented."

    VARIATION       sysORUpTime
    ACCESS          not-implemented
    DESCRIPTION
        "This object is not implemented."

    VARIATION       sysORDescr
    ACCESS          not-implemented
    DESCRIPTION
        "This object is not implemented."

    VARIATION       coldStart
    DESCRIPTION
        "A coldStart trap is generated on RPMS entity reboots."

    ::= { ciscoSnmpV2Capability 2 }

ciscoMgxSnmpV2CapabilityV20 AGENT-CAPABILITIES
    PRODUCT-RELEASE "MGX8850 Release 2.0.00"
    STATUS          current
    DESCRIPTION
        "SNMPv2-MIB capabilities in MGX Series."

    SUPPORTS        SNMPv2-MIB
    INCLUDES        {
                        snmpGroup,
                        systemGroup,
                        snmpCommunityGroup,
                        snmpBasicNotificationsGroup
                    }
    VARIATION       sysName
    SYNTAX          DisplayString (SIZE (1..32))
    DESCRIPTION
        "The maximum length supported for the
        name is 32 characters."

    VARIATION       sysORLastChange
    ACCESS          not-implemented
    DESCRIPTION
        "Not supported."

    VARIATION       sysORID
    ACCESS          not-implemented
    DESCRIPTION
        "Not supported."

    VARIATION       sysORUpTime
    ACCESS          not-implemented
    DESCRIPTION
        "Not supported."

    VARIATION       sysORDescr
    ACCESS          not-implemented
    DESCRIPTION
        "Not supported."

    ::= { ciscoSnmpV2Capability 3 }

ciscoBpxSesSnmpV2CapabilityV10 AGENT-CAPABILITIES
    PRODUCT-RELEASE "Cisco BPX SES Release 1.0.00"
    STATUS          current
    DESCRIPTION
        "SNMPv2-MIB capabilities."

    SUPPORTS        SNMPv2-MIB
    INCLUDES        {
                        snmpGroup,
                        systemGroup,
                        snmpCommunityGroup,
                        snmpBasicNotificationsGroup
                    }
    VARIATION       sysName
    SYNTAX          DisplayString (SIZE (1..8))
    DESCRIPTION
        "The maximum length supported for the
        name is 8 characters."

    VARIATION       sysORLastChange
    ACCESS          not-implemented
    DESCRIPTION
        "Not supported."

    VARIATION       sysORID
    ACCESS          not-implemented
    DESCRIPTION
        "Not supported."

    VARIATION       sysORUpTime
    ACCESS          not-implemented
    DESCRIPTION
        "Not supported."

    VARIATION       sysORDescr
    ACCESS          not-implemented
    DESCRIPTION
        "Not supported."

    ::= { ciscoSnmpV2Capability 4 }

ciscoSnmpV2CapCatOSV08R0301 AGENT-CAPABILITIES
    PRODUCT-RELEASE "Cisco CatOS 8.3(1) for Catalyst 6000/6500
                          and Cisco 7600 series devices."
    STATUS          current
    DESCRIPTION
        "SNMPv2-MIB capabilities."

    SUPPORTS        SNMPv2-MIB
    INCLUDES        {
                        snmpGroup,
                        snmpCommunityGroup,
                        snmpSetGroup,
                        systemGroup,
                        snmpBasicNotificationsGroup,
                        snmpObsoleteGroup
                    }
    VARIATION       authenticationFailure
    DESCRIPTION
        "The instance values of
        csySnmpAuthFailAddressType and
        csySnmpAuthFailAddress as defined in
        CISCO-SYSTEM-MIB are appended to this
        notification."

    ::= { ciscoSnmpV2Capability 5 }

ciscoSnmpV2CapCatOSV08R0601 AGENT-CAPABILITIES
    PRODUCT-RELEASE "Cisco CatOS 8.6(1) for Catalyst 6000/6500
                          and Cisco 7600 series devices."
    STATUS          current
    DESCRIPTION
        "SNMPv2-MIB capabilities."

    SUPPORTS        SNMPv2-MIB
    INCLUDES        {
                        snmpGroup,
                        snmpSetGroup,
                        systemGroup,
                        snmpCommunityGroup,
                        snmpBasicNotificationsGroup,
                        snmpWarmStartNotificationGroup,
                        snmpObsoleteGroup
                    }
    VARIATION       authenticationFailure
    DESCRIPTION
        "The instance values of
        csySnmpAuthFailAddressType and
        csySnmpAuthFailAddress as defined in
        CISCO-SYSTEM-MIB are appended to this
        notification."

    ::= { ciscoSnmpV2Capability 6 }

ciscoSnmpV2CapACSWV03R000 AGENT-CAPABILITIES
    PRODUCT-RELEASE "ACSW (Application Control Software) 3.0
                          for Application Control Engine (ACE)
                          Service Module."
    STATUS          current
    DESCRIPTION
        "SNMPv2-MIB capabilities."

    SUPPORTS        SNMPv2-MIB
    INCLUDES        {
                        snmpGroup,
                        snmpCommunityGroup,
                        systemGroup,
                        snmpBasicNotificationsGroup
                    }
    VARIATION       snmpEnableAuthenTraps
    ACCESS          read-only
    DESCRIPTION
        "Set operation not supported via SNMP."

    VARIATION       sysContact
    ACCESS          read-only
    DESCRIPTION
        "Set operation not supported via SNMP."

    VARIATION       sysName
    ACCESS          read-only
    DESCRIPTION
        "Set operation not supported via SNMP."

    VARIATION       sysLocation
    ACCESS          read-only
    DESCRIPTION
        "Set operation not supported via SNMP."

    VARIATION       coldStart
    DESCRIPTION
        "The instance values of clogOriginIDType and
        clogOriginID as defined in CISCO-SYSLOG-MIB
        are appended to this notification. This helps
        in recognizing the device from which the
        notification is generated."

    VARIATION       authenticationFailure
    DESCRIPTION
        "The instance values of clogOriginIDType and
        clogOriginID as defined in CISCO-SYSLOG-MIB
        are appended to this notification. This helps
        in recognizing the device from which the
        notification is generated."

    ::= { ciscoSnmpV2Capability 7 }

ciscoSnmpV2Capc4710aceVA1R700 AGENT-CAPABILITIES
    PRODUCT-RELEASE "ACSW (Application Control Software) A1(7)
                    for ACE 4710 Application Control Engine
                    Appliance."
    STATUS          current
    DESCRIPTION
        "SNMPv2-MIB capabilities."

    SUPPORTS        SNMPv2-MIB
    INCLUDES        {
                        snmpGroup,
                        snmpCommunityGroup,
                        systemGroup,
                        snmpBasicNotificationsGroup
                    }
    VARIATION       snmpEnableAuthenTraps
    ACCESS          read-only
    DESCRIPTION
        "Set operation not supported via SNMP."

    VARIATION       sysContact
    ACCESS          read-only
    DESCRIPTION
        "Set operation not supported via SNMP."

    VARIATION       sysName
    ACCESS          read-only
    DESCRIPTION
        "Set operation not supported via SNMP."

    VARIATION       sysLocation
    ACCESS          read-only
    DESCRIPTION
        "Set operation not supported via SNMP."

    VARIATION       coldStart
    DESCRIPTION
        "The instance values of clogOriginIDType and
        clogOriginID as defined in CISCO-SYSLOG-MIB
        are appended to this notification. This helps
        in recognizing the device from which the
        notification is generated."

    VARIATION       authenticationFailure
    DESCRIPTION
        "The instance values of clogOriginIDType and
        clogOriginID as defined in CISCO-SYSLOG-MIB
        are appended to this notification. This helps
        in recognizing the device from which the
        notification is generated."

    ::= { ciscoSnmpV2Capability 8 }

END
