-- *****************************************************************
-- CISCO-SNMP-MPD-CAPABILITY.my:
-- Cisco SNMP-MPD-MIB AGENT-CAPABILITIES
--
-- July 2003, Binh Le
-- May 2006, Roopeshakumar Shalgar
--
-- Copyright (c) 2003-2004, 2006, 2008 by Cisco Systems, Inc.
-- All rights reserved.
-- *****************************************************************

CISCO-SNMP-MPD-CAPABILITY DEFINITIONS ::= BEGIN

IMPORTS
    MODULE-IDENTITY
        FROM SNMPv2-SMI
    AGENT-CAPABILITIES
        FROM SNMPv2-CONF
    ciscoAgentCapability
        FROM CISCO-SMI;


ciscoSnmpMpdCapability MODULE-IDENTITY
    LAST-UPDATED    "200802110000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com, cs-snmp@cisco.com"
    DESCRIPTION
        "The capabilities description of SNMP-MPD-MIB."
    REVISION        "200802110000Z"
    DESCRIPTION
        "Added capability statement
        cSnmpMpdCapabilityc4710aceVA1R700 for ACE
        4710 Application Control Engine Appliance."
    REVISION        "200605270000Z"
    DESCRIPTION
        "Added capability statement
        cSnmpMpdCapabilityACSWV03R000 for
        Application Control Engine (ACE)."
    REVISION        "200401300000Z"
    DESCRIPTION
        "Initial version of this MIB module."
    ::= { ciscoAgentCapability 317 }



cSnmpMpdCapabilityCatOSV05R0401 AGENT-CAPABILITIES
    PRODUCT-RELEASE "Cisco CatOS 5.4(1)."
    STATUS          current
    DESCRIPTION
        "SNMP-MPD-MIB capabilities."

    SUPPORTS        SNMP-MPD-MIB
    INCLUDES        { snmpMPDGroup }
    ::= { ciscoSnmpMpdCapability 1 }

cSnmpMpdCapabilityACSWV03R000 AGENT-CAPABILITIES
    PRODUCT-RELEASE "ACSW (Application Control Software) 3.0"
    STATUS          current
    DESCRIPTION
        "SNMP-MPD-MIB capabilities."

    SUPPORTS        SNMP-MPD-MIB
    INCLUDES        { snmpMPDGroup }
    ::= { ciscoSnmpMpdCapability 2 }

cSnmpMpdCapabilityc4710aceVA1R700 AGENT-CAPABILITIES
    PRODUCT-RELEASE "ACSW (Application Control Software) A1(7)
                     for ACE 4710 Application Control Engine
                     Appliance."
    STATUS          current
    DESCRIPTION
        "SNMP-MPD-MIB capabilities."

    SUPPORTS        SNMP-MPD-MIB
    INCLUDES        { snmpMPDGroup }
    ::= { ciscoSnmpMpdCapability 3 }

END
