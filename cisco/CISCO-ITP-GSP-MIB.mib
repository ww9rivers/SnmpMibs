-- *****************************************************************
-- CISCO-ITP-GSP-MIB: Itp Signalling Point
--
-- August 2002,  John Linton, Shekhar Acharya
--
-- Copyright (c) 2002-2003, 2005, 2008-2010 by Cisco Systems Inc.
-- All rights reserved.
-- *****************************************************************

CISCO-ITP-GSP-MIB DEFINITIONS ::= BEGIN

IMPORTS
    Counter32,
    Integer32,
    Gauge32,
    MODULE-IDENTITY,
    NOTIFICATION-TYPE,
    OBJECT-TYPE,
    Unsigned32
        FROM SNMPv2-SMI
    MODULE-COMPLIANCE,
    NOTIFICATION-GROUP,
    OBJECT-GROUP
        FROM SNMPv2-CONF
    SnmpAdminString
        FROM SNMP-FRAMEWORK-MIB
    InetAddressType,
    InetAddress,
    InetPortNumber
        FROM INET-ADDRESS-MIB
    InterfaceIndexOrZero
        FROM IF-MIB
    RowStatus,
    TimeStamp,
    TruthValue,
    TEXTUAL-CONVENTION
        FROM SNMPv2-TC
    CItpTcAclId,
    CItpTcCLLI,
    CItpTcDisplayPC,
    CItpTcInstanceNumber,
    CItpTcLinksetId,
    CItpTcNetworkName,
    CItpTcLinkSLC,
    CItpTcLinkType,
    CItpTcNetworkIndicator,
    CItpTcPointCode,
    CItpTcPointCodeType,
    CItpTcQos,
    CItpTcRouteTableName,
    CItpTcServiceIndicator
        FROM CISCO-ITP-TC-MIB
    ciscoMgmt
        FROM CISCO-SMI;


ciscoGspMIB MODULE-IDENTITY
    LAST-UPDATED    "201003050000Z"
    ORGANIZATION    "Cisco Systems, Inc."
    CONTACT-INFO
            "Cisco Systems, Inc
            Customer Service

            Postal: 170 W. Tasman Drive
            San Jose, CA  95134
            USA

            Tel: +1 800 553-NETS

            E-mail: cs-ss7@cisco.com"
    DESCRIPTION
        "The MIB for managing Signalling Points and its
        associated messages transported over Signalling
        System  No. 7 (SS7) Network via Cisco IP Transfer
        Point.  This MIB replaces the CISCO-ITP-SP-MIB and
        provide support multiple instances of a signalling
        point within same configuration.

        The Cisco IP Transfer Point (ITP) is a hardware
        and software solution that transports SS7 traffic
        using IP. Each ITP node provides function similar
        to SS7 Signalling point.

        The relevant ITU documents describing this technology
        is the ITU Q series, including ITU Q.700: Introduction
        to CCITT Signalling System No. 7 and ITU Q.701
        Functional description of the message transfer part
        (MTP) of Signalling System No. 7.

        This MIB models the GSP as follows:


        Abbreviations:
        AERM  - Alignment Error Rate Monitor
        CLLI  - Common-Language Location Identification
        DPC   - Destination Point Code
        GSP   - Gateway Signalling Point
        HSL   - High Speed Link (ATM based)
        LLSC  - link set control
        LSAC  - Signalling link activity control
        LSDA  - Signalling data link allocation
        LSLA  - Signalling link activation
        LSLD  - Signalling link deactivation
        LSLR  - Signalling link restoration
        LSSU  - Link Status Signal Unit
        LSTA  - Signalling terminal allocation
        MTP   - Message Transport Protocol
        MTP2  - Layer 2 of Message Transport Protocol
        MTP3  - Layer 3 of Message Transport Protocol
        NTT   - The Japanese Nippon Telephone & Telegraph
        OPC   - Originating Point Code
        PC    - Point Code
        RTN   - RouteTableName
        SCTP  - Stream Transmission Protocol(RFC 2960)
        SIB   - Status Indicator Busy
        SLT   - Signalling Link Test
        SLTA  - Signalling Link Test Acknowledgement
        SP    - Signalling Point
        SS7   -  System  No. 7 (SS7) Network
        SUERM - Signal Unit Error Rate Monitor
        TCBC  - Changeback control
        TCOC  - Changeover control
        TCRC  - Controlled rerouting control
        TFRC  - Forced rerouting control
        TLAC  - Link availability control
        TPRC  - Signalling point restart control
        TRCC  - Signalling route set congestion control
        TSFC  - Signalling traffic flow control
        TSRC  - Signalling routing control
        TTC   - The Japanese Telecommunications Technology
          Committee
        WRR   - Weighted round robin"
    REVISION        "200912310000Z"
    DESCRIPTION
        "Added the cgspLinkRxCongestionState object into CgspLinkTableEntry and
        ciscoGspRxCongestionChange notification to notify state of cgspLinkRxCongestionState."
    REVISION        "200909120000Z"
    DESCRIPTION
        "Added the opc value to the cgspInstSccpWrrOption textual convention."
    REVISION        "200905250000Z"
    DESCRIPTION
        "Added the following objects into cgspInstanceTableEntry
        for GTT weighted loadshare.
        cgspInstSccpWrrOpcShift,
        cgspInstSccpWrrOption"
    REVISION        "200805070000Z"
    DESCRIPTION
        "Added the following objects into CgspLinkTableEntry
        for additional Q752 related reporting.
        cgspLinkQ752T1E12,
        cgspLinkQ752T1E12Errors,
        cgspLinkQ752T2E11,
        cgspLinkQ752T2E17,
        cgspLinkQ752T2E19.
        Added linkRestored(34) and linkTestFailure(35) reason code to the
        cgspLinkReason object.

        Added the following textual convention:
        CgspDisplayInstanceUserPart.

        Added a new table cgspInstUPUTable with following objects:
        cgspMtp3SI, cgspInstSIUPUReceived, cgspInstSIUPUTransmitted,
        cgspInstUserPartDisplay.

        Added the following objects:
        cgspNotificationsInfo, cgspUPUNotifWindowTime.

        Added following new notifications:
        ciscoGspUPUReceived, ciscoGspUPUTransmitted.

        Added the following cgspNotificationsInfo objects:
        cgspUPUIntervalDuration, cgspIntervalUPUs."
    REVISION        "200510210000Z"
    DESCRIPTION
        "Added new set of enums (from timerMtp2T01 to
        timerMtp2T07) to TC CgspTimerNumbers for
        MTP2 timers specified in ITU Q.703."
    REVISION        "200502240000Z"
    DESCRIPTION
        "Added new ciscoGspIsolation notification to indicate
        when MTP3 node becomes isolated."
    REVISION        "200307160000Z"
    DESCRIPTION
        "Additional reason codes to the cgspLinkReason object
        and updated CgspSS7Variant textual convention to
        support NTT and TTC Japanese variants.  Also, update
        REFERENCE clauses to indicate support for appropriate
        ANSI standard."
    REVISION        "200303030000Z"
    DESCRIPTION
        "Initial version of this MIB module."
    ::= { ciscoMgmt 336 }


-- Top-level structure of the MIB

ciscoGspMIBNotifs  OBJECT IDENTIFIER
    ::= { ciscoGspMIB 0 }

ciscoGspMIBObjects  OBJECT IDENTIFIER
    ::= { ciscoGspMIB 1 }

ciscoGspMIBConform  OBJECT IDENTIFIER
    ::= { ciscoGspMIB 2 }

cgspScalars  OBJECT IDENTIFIER
    ::= { ciscoGspMIBObjects 1 }

cgspProfile  OBJECT IDENTIFIER
    ::= { ciscoGspMIBObjects 2 }

cgspInstance  OBJECT IDENTIFIER
    ::= { ciscoGspMIBObjects 3 }

cgspPointCode  OBJECT IDENTIFIER
    ::= { ciscoGspMIBObjects 4 }

cgspLinkset  OBJECT IDENTIFIER
    ::= { ciscoGspMIBObjects 5 }

cgspLink  OBJECT IDENTIFIER
    ::= { ciscoGspMIBObjects 6 }

cgspNotificationsEnable  OBJECT IDENTIFIER
    ::= { ciscoGspMIBObjects 7 }

cgspNotificationsInfo  OBJECT IDENTIFIER
    ::= { ciscoGspMIBObjects 8 }


-- **************************************************************
-- *                                                            *
-- * Textual Conventions                                        *
-- *                                                            *
-- **************************************************************

CgspSequenceNumber ::= TEXTUAL-CONVENTION
    STATUS          current
    DESCRIPTION
        "This textual convention defines all of the allowed
        values for a sequence of integers used by the
        SS7 protocol to transmit and acknowledge packets.
        The range is specified from 0 to maximum allowed
        value for extended sequence numbers.  The actual
        range will depend on the type of link and
        the variant.  The value will increase and then wrap
        to the zero value.  The following are examples of
        valid sequences.
        0..126,127,0..
        0..254,255,0..
        0..32766,32767,0..
        0..65534,65535,0..
        Therefore, the sequence number will behave like
        a counter with range appropriate for the type of
        link."
    SYNTAX          Unsigned32 (0..65535)

CgspSampleInterval ::= TEXTUAL-CONVENTION
    STATUS          current
    DESCRIPTION
        "This textual convention defines the allowed values
        for a sample interval.  This value is specified in
        seconds and ranges from 1 minute to 1 hour."
    SYNTAX          Unsigned32 (60..3600)

CgspPercentThreshold ::= TEXTUAL-CONVENTION
    STATUS          current
    DESCRIPTION
        "This textual convention defines the allowed values
        used to define a threshold.  This value is
        specified as percentage of link utilization.  A
        value of zero indicates that this specific
        threshold is to be ignored."
    SYNTAX          Unsigned32 (0..100)

CgspLinkTestResults ::= TEXTUAL-CONVENTION
    STATUS          current
    DESCRIPTION
        "This object provides information on result from
        signalling link test procedures as follows.
          'noErrors'     : Link test did not detect any errors.
          'undefinedOpc' : A signalling link test message was
                           received with an undefined originating
                           point code.
          'incorrectOpc' : A signalling link test message was
                           received with an incorrect originating
                           point code.
          'undefinedSlc' : A signalling link test message was
                           received with an undefined signalling
                           link code.
          'incorrectSlc' : A signalling link test message was
                           received with an incorrect signalling
                           link code..
          'incorrectNi'  : A signalling link test message was
                           received with an incorrect Network
                           Indicator.
          'badPattern'   : A signalling link test message was
                           received with an incorrect test
                           pattern. This may be caused by variant
                           mismatched or incorrect definitions
                           on physical link.
          'nonAdjacent'   :Received a signalling link test message
                           from an non-adjacent node.
          'failed'        :Unable to run test or no response was
                           received within the specified interval."
    SYNTAX          INTEGER  {
                        noErrors(0),
                        undefinedOpc(1),
                        incorrectOpc(2),
                        undefinedSlc(3),
                        incorrectSlc(4),
                        incorrectNi(5),
                        badPattern(6),
                        nonAdjacent(7),
                        failed(8)
                    }

CgspLinkUtilization ::= TEXTUAL-CONVENTION
    STATUS          current
    DESCRIPTION
        "This textual convention defines a range of values
        that represent a link's utilization during an
        interval of time.  The values expressed as a
        percent of link capacity.  Any value over 999 will
        be represented as 999.

        For SS7 links based on IP/SCTP the link capacity
        is not directly related to the interface speed used
        to transmit packets.  This is different from serial
        and HSL links.  The capacity of these types of
        links depend on the amount of resources available
        in the IP cloud.  The IP cloud must be provisioned
        to support traffic for all SS7 links. In order to
        monitor link utilization on IP/SCTP based SS7 links
        a planned capacity must be specified.  If this value
        is incorrectly estimated or traffic exceeds this
        expected value link utilization may exceed 100
        percent.  This is possible because the IP cloud
        may be provisioned with additional capacity or
        may discard less important traffic based on QoS
        parameters.

        When a SS7 link has not be configured for link
        utilization monitoring this value object will
        have a value of zero."
    SYNTAX          Gauge32 (0..999)

CgspLinkCapacity ::= TEXTUAL-CONVENTION
    STATUS          current
    DESCRIPTION
        "This textual convention defines the planned
        capacity of a SS7 link in bit per second.

        When the cgspLinkType object is 'sctpIp' or
        'hsl' the link capacity can be obtained from
        information in the IF-MIB.

        When the cgspLinkType object is 'sctpIp' a
        value of zero indicates that link utilization
         should not be calculated for this SS7 link."
    SYNTAX          Unsigned32 (0..0 | 56000..2147483647)

CgspProfileName ::= TEXTUAL-CONVENTION
    STATUS          current
    DESCRIPTION
        "The configured name associated with a Signalling
        Point Profile.

        An octet string specified by an administrator that must
        be in human-readable form.  The names must conform to
        the allowed characters that can be specified via
        Command Line Interface(CLI).  The names cannot contain
        control character and should not contain leading or
        trailing white space."
    SYNTAX          OCTET STRING (SIZE (0..19))

CgspLinkUtilizationState ::= TEXTUAL-CONVENTION
    STATUS          current
    DESCRIPTION
        "Link Utilization State as follows:
        'unMonitored'    - traffic for a specified direction
                           is not being monitored.
        'underThreshold' - traffic for a specified direction
                           on a link is below the specified
                           threshold.

        'overThreshold'  - traffic for a specified direction
                           on a link is above to or exceeds
                           the specified threshold."
    SYNTAX          INTEGER  {
                        unMonitored(0),
                        underThreshold(1),
                        overThreshold(2)
                    }

CgspTimerNumbers ::= TEXTUAL-CONVENTION
    STATUS          current
    DESCRIPTION
        "Enumerated values for all timers"
    SYNTAX          INTEGER  {
                        timerMtp3T01(1), -- Delay to avoid message
                                         -- mis-sequencing on changeover.
                        timerMtp3T02(2), -- Waiting for changeover
                                         -- acknowledgement.
                        timerMtp3T03(3), -- Time controlled
                                         -- diversion-delay to avoid
                                         -- mis-sequencing on change back.
                        timerMtp3T04(4), -- Waiting for change back
                                         -- acknowledgement (first
                                         -- attempt).
                        timerMtp3T05(5), -- Waiting for change back
                                         -- acknowledgement (second
                                         -- attempt)
                        timerMtp3T06(6), -- Delay to avoid message
                                         -- mis-sequencing on controlled
                                         -- rerouting
                        timerMtp3T07(7), -- Waiting for signalling data
                                         -- link connection
                                         -- acknowledgement
                        timerMtp3T08(8), -- Transfer prohibited inhibition
                                         -- timer (transient solution)
                        timerMtp3T09(9), -- Reserved
                        timerMtp3T10(10), -- Waiting to repeat signalling
                                          -- routeset test message
                        timerMtp3T11(11), -- Transfer restricted timer
                        timerMtp3T12(12), -- Waiting for uninhibit
                                          -- acknowledgement
                        timerMtp3T13(13),
                        timerMtp3T14(14), -- Waiting for inhibition
                                          -- acknowledgement
                        timerMtp3T15(15), -- Waiting to start signalling
                                          -- routeset congestion
                        timerMtp3T16(16), -- Waiting for routeset
                                          -- congestion status update
                        timerMtp3T17(17), -- Delay to avoid oscillation of
                                          -- initial alignment failure and
                                          -- link restart
                        timerMtp3T18(18), -- ANSI: Repeat TFR once by
                                          -- response method ITU: MTP
                                          -- restart link supervision
                        timerMtp3T19(19), -- ANSI: failed craft timer
                                          -- referral timer ITU:
                                          -- supervision timer during MTP
                                          -- restart
                        timerMtp3T20(20), -- ANSI: waiting to repeat local
                                          -- inhibit test ITU: MTP restart
                                          -- timer at the signalling point
                        timerMtp3T21(21), -- ANSI: waiting to repeat
                                          -- remote inhibit test) ITU: MTP
                                          -- restart timer at adjacent
                                          -- signalling point
                        timerMtp3T22(22), -- ANSI: restarting SP waiting
                                          -- for signalling links avail
                                          -- ITU: local inhibit test timer
                        timerMtp3T23(23), -- ANSI: restarting SP waiting
                                          -- to receive all TRA msgs ITU:
                                          -- remote inhibit test timer
                        timerMtp3T24(24), -- ANSI: restarting SP waiting
                                          -- to broadcast all TRA msgs
                                          -- ITU: stabilizing timer after
                                          -- local processor outage
                        timerMtp3T25(25), -- Timer at Signalling Point
                                          -- (SP) adjacent to restarting
                                          -- Signalling Point, waiting for
                                          -- traffic restart allowed
                                          -- message.
                        timerMtp3T26(26), -- Timer at restarting SP
                                          -- waiting to repeat traffic
                                          -- restart waiting message.
                        timerMtp3T27(27), -- Minimum duration of
                                          -- unavailability for full
                                          -- restart
                        timerMtp3T28(28), -- Timer at SP adjacent to
                                          -- restarting SP waiting for
                                          -- traffic restart waiting
                                          -- message
                        timerMtp3T29(29), -- Timer started when TRA sent
                                          -- in response to unexpected TRA
                                          -- or TRW
                        timerMtp3T30(30), -- Timer to limit sending of
                                          -- TFPs and TFRs in response to
                                          -- unexpected TRA or TRW
                        timerMtp3T31(31), -- False link congestion
                                          -- detection timer
                        timerMtp3T32(32), -- Link oscillation timer -
                                          -- Procedure A
                        timerMtp3T33(33), -- Probation timer for link
                                          -- oscillation - Procedure B
                        timerMtp3T34(34), -- Suspension timer for link
                                          -- oscillation - Procedure B
                        timerLinkTest(35), -- Signalling Link Test
                                           -- Acknowledgement timer
                        timerLinkMessag1(36), -- Interval timer for
                                              -- sending test messages
                        timerLinkActRetry(37), -- Link activation retry
                                               -- timer.
                        timerMtp2T01(38), -- Link alignment ready timer
                        timerMtp2T02(39), -- Link not aligned timer
                        timerMtp2T03(40), -- Link aligned timer
                        timerMtp2T04N(41), -- Link proving normal timer
                        timerMtp2T04E(42),
                        timerMtp2T05(43), -- Sending SIB timer
                        timerMtp2T06(44), -- Remote congestion timer
                        timerMtp2T07(45)
                    }

CgspTimerValue ::= TEXTUAL-CONVENTION
    STATUS          current
    DESCRIPTION
        "Value of timers in milliseconds as follows.  A value of zero
        indicates that the timer is not applicable for variant or
        link type.  The values specified in this textual convention
        apply to the various timers identified in CgspTimerNumbers
        textual convention.
                                    ANSI                     ITU
                             Min    Max    Def     Min    Max    Def
                             ------ ------ ------  ------ ------ ------
         TimerMtp3T01           500   1200    800     500   1200    800
         TimerMtp3T02           700   2000   1400     700   2000   1400
         TimerMtp3T03           500   1200    800     500   1200    800
         TimerMtp3T04           500   1200    800     500   1200    800
         TimerMtp3T05           500   1200    800     500   1200    800
         TimerMtp3T06           500   1200    800     500   1200    800
         TimerMtp3T07          1000   2000   1500    1000   2000   1500
         TimerMtp3T08           800   1200   1000     800   1200   1000
         TimerMtp3T10         30000  60000  45000   30000  60000  45000
         TimerMtp3T11         30000  90000  60000   30000  90000  60000
         TimerMtp3T12           800   1500   1150     800   1500   1150
         TimerMtp3T13           800   1500   1150     800   1500   1150
         TimerMtp3T14          2000   3000   2500    2000   3000   2500
         TimerMtp3T15          2000   3000   2500    2000   3000   2500
         TimerMtp3T16          1400   2000   1700    1400   2000   1700
         TimerMtp3T17           800   1500   1150     800   1500   1150
         TimerMtp3T18          2000  20000  11000    1000  31000  30000
         TimerMtp3T19        480000 600000 540000   67000  69000  68000
         TimerMtp3T20         90000 120000 105000    1000  61000  60000
         TimerMtp3T21         90000 120000 105000   63000  65000  64000
         TimerMtp3T22         36000  60000  30000   80000 360000 300000
         TimerMtp3T23          9000  60000  30000   80000 360000 300000
         TimerMtp3T24          9000  60000  30000     500    500    500
         TimerMtp3T25         30000  35000  30000     n/a    n/a    n/a
         TimerMtp3T26         12000  15000  12000     n/a    n/a    n/a
         TimerMtp3T27          2000  50000   4000     n/a    n/a    n/a
         TimerMtp3T28          3000  35000  30000     n/a    n/a    n/a
         TimerMtp3T29         60000  65000  63000     n/a    n/a    n/a
         TimerMtp3T30         30000  35000  33000     n/a    n/a    n/a
         TimerMtp3T31         10000 120000  60000     n/a    n/a    n/a
         TimerMtp3T32          5000 120000  60000     n/a    n/a    n/a
         TimerMtp3T33         60000 600000 300000     n/a    n/a    n/a
         TimerMtp3T34          5000 120000  60000     n/a    n/a    n/a
         TimerLinkTest         4000  12000   8000     n/a    n/a    n/a
         TimerLinkMessage     30000  90000  60000     n/a    n/a    n/a
         TimerLinkActRetry    60000  90000  60000     n/a    n/a    n/a"

    REFERENCE
        "ITU Q.703 Signalling Link.
            ANSI T1.111.3 Telecommunications - signalling system
            No. 7 (SS7)-Message Transfer Part (MTP)."
    SYNTAX          Unsigned32 (0..0 | 1..4294967295)

CgspSS7Variant ::= TEXTUAL-CONVENTION
    STATUS          current
    DESCRIPTION
        "The list of SS7 variants.
        'unknown' : Unknown or undefined variant.
        'ANSI'    : The ANSI variant of the SS7 specification.
        'ITU'     : The ITU variant of the SS7 specification.
        'China'   : The China national variant. This variant
                    is a combination of ITU and ANSI. The
                    protocol matches ITU except where the
                    point-code has been expanded to ANSI format.
        'NTT'     : The Japanese Nippon Telephone & Telegraph
                    variant.
        'TTC'     : The Japanese Telecommunications Technology
                    Committee variant."

    REFERENCE
        "GF 001-9001 - Technical Specifications of Signalling
             System No. 7 for National Telephone Network of China."
    SYNTAX          INTEGER  {
                        unknown(0),
                        ansi(1),
                        itu(2),
                        china(3),
                        ntt(4),
                        ttc(5)
                    }

CgspDisplayInstanceUserPart ::= TEXTUAL-CONVENTION
    STATUS          current
    DESCRIPTION
        "The instance name and user part information
        formatted for display. If instance name is not
        configured, the default local point code in
        ASCII string format will be provided as instance
        name."
    SYNTAX          OCTET STRING (SIZE (0..40))

CItpTcSccpWrrOption ::= TEXTUAL-CONVENTION
    STATUS          current
    DESCRIPTION
        "The possible options for calculate sccp class1 traffic
        loadshare when GTT application group's multiplicity mode
        is WRR(Weighted round robin):
        'sls'     : Use sls to calculate loadsharing
        'cgpaSls' : Use the combination of cgpa and sls to calculate loadsharing
        'opcSls'  : Use the combination of opc and sls to calculate loadsharing
        'opc'     : Use the opc to caculate loadsharing"
    SYNTAX          INTEGER  {
                        sls(0),
                        cgpaSls(1),
                        opcSls(2),
                        opc(3)
                    }

-- *************************************************************
-- *                                                           *
-- * GSP - Scalar                                              *
-- *                                                           *
-- *************************************************************

cgspCLLICode OBJECT-TYPE
    SYNTAX          CItpTcCLLI
    MAX-ACCESS      read-write
    STATUS          current
    DESCRIPTION
        "Common-Language Location Identification Codes
        (CLLI Codes).  This object identifies the
        physical location of this device and can provide
        additional informaton on the device type."
    ::= { cgspScalars 1 }

cgspUtilSampleInterval OBJECT-TYPE
    SYNTAX          CgspSampleInterval
    UNITS           "seconds"
    MAX-ACCESS      read-write
    STATUS          current
    DESCRIPTION
        "This object specifies the time interval used to monitor
        the utilization of SS7 links.  This object in combination
        with cgspUtilThreshold, cgspLinkPlanCapacitySent and
        cgspLinkPlanCapacityRcvd will be used to calculate
        utilization of SS7 links.  Changes to the polling interval
        will take effect after the completion of the current
        sample interval."
    DEFVAL          { 300 }
    ::= { cgspScalars 2 }

cgspUtilThreshold OBJECT-TYPE
    SYNTAX          CgspPercentThreshold
    UNITS           "percent"
    MAX-ACCESS      read-write
    STATUS          current
    DESCRIPTION
        "This object specifies the threshold of usage for all
        SS7 links in SP.  This object is used to determine when
        to generate the ciscoGspLinkRcvdUtilChange or
        ciscoGspLinkSentUtilChange notifications.

        A value of zero indicates that no default threshold
        is specified.  Therefore, only links with non-zero
        values for cgspLinkUtilThresholdRcvd or
        cgspLinkUtilThresholdSent will generate notifications
        based on link utilization.

        Changes to the utilization threshold will take effect
        at the end of the current interval."
    DEFVAL          { 40 }
    ::= { cgspScalars 3 }

cgspUtilAbateDelta OBJECT-TYPE
    SYNTAX          CgspPercentThreshold
    UNITS           "percent"
    MAX-ACCESS      read-write
    STATUS          current
    DESCRIPTION
        "This object allows the falling threshold to be lower
        than the rising threshold when calculating whether to
        generate the ciscoGspLinkRcvdUtilChange or
        ciscoGspLinkSentUtilChange notifications.  This is done
        to prevent generating notifications for slight changes
        in traffic."
    DEFVAL          { 0 }
    ::= { cgspScalars 4 }

cgspPlanCapacityDefault OBJECT-TYPE
    SYNTAX          CgspLinkCapacity
    UNITS           "bits per second"
    MAX-ACCESS      read-write
    STATUS          current
    DESCRIPTION
        "This object provides a default for value for links
        with a cgspLinkType='sctpIp'.  For all other types
        of linkset this value is ignored.  When a linkset
        based on SCTP/IP and the values for the
        cgspLinkPlanCapacityRcvd or cgspLinkPlanCapacitySent
        object are zero then this object will be used
        as the default.  A value of zero indicates that
        a global default has not been specified.

        This object will be used in combination with
        cgspUtilSampleInterval, cgspUtilThreshold, cgspUtilThreshold
        and cgspLinkUtilThresholdRcvd to generate the
        ciscoGspLinkRcvdUtilChange notification."
    ::= { cgspScalars 5 }

cgspEventSequenceNumber OBJECT-TYPE
    SYNTAX          Counter32
    UNITS           "events"
    MAX-ACCESS      read-only
    STATUS          current
    DESCRIPTION
        "Each event or notification is required to provide a
        sequence number to be used by the NMS to determine when
        messages from a particular device are missing.  This value
        will included in each SS7 notification issued by this device."
    REFERENCE       "GR-82-CORE 6.6.1 Event Report Content R6-33"
    ::= { cgspScalars 6 }

cgspUPUNotifWindowTime OBJECT-TYPE
    SYNTAX          Integer32 (60..86400)
    UNITS           "seconds"
    MAX-ACCESS      read-write
    STATUS          current
    DESCRIPTION
        "This object specifies the time interval used to monitor
        the ciscoGspUPUReceived and ciscoGspUPUTransmitted
        notifications for specific user part and signalling point
        instance.  The first occurrence of ciscoGspUPUReceived and
        ciscoGspUPUTransmitted notifications are sent and the
        further occurrences of notifications in this interval
        are suppressed.

        At the end of this interval, a notification is sent with
        total number of UPU MSUs transmitted or received during
        this interval."
    DEFVAL          { 900 }
    ::= { cgspScalars 7 }
-- *************************************************************
-- *                                                           *
-- * Profile Table                                             *
-- *                                                           *
-- *************************************************************

cgspProfileTable OBJECT-TYPE
    SYNTAX          SEQUENCE OF CgspProfileTableEntry
    MAX-ACCESS      not-accessible
    STATUS          current
    DESCRIPTION
        "A table that contains the Profiles of signalling
        points.  Entries are added to this table via
        cgspProfileRowStatus in accordance with the RowStatus
        convention."
    ::= { cgspProfile 1 }

cgspProfileTableEntry OBJECT-TYPE
    SYNTAX          CgspProfileTableEntry
    MAX-ACCESS      not-accessible
    STATUS          current
    DESCRIPTION
        "A list of Profile attributes.  Profiles are
        used to specify common configuration options for
        SS7 links without customizing each link.
        A profile is created with the specified values
        using this table and the cgspProfileTimerTable
        Table.  The common values are applied to all
        links in a linkset by specifying the
        cgspLinksetProfileName on the linkset."
    INDEX           { cgspProfileName }
    ::= { cgspProfileTable 1 }

CgspProfileTableEntry ::= SEQUENCE {
        cgspProfileName               CgspProfileName,
        cgspProfileVariant            CgspSS7Variant,
        cgspProfileMtp2BundleTimer    Integer32,
        cgspProfileMtp2SendQueueDepth Integer32,
        cgspProfileRowStatus          RowStatus
}

cgspProfileName OBJECT-TYPE
    SYNTAX          CgspProfileName
    MAX-ACCESS      not-accessible
    STATUS          current
    DESCRIPTION
        "Name of the profile."
    ::= { cgspProfileTableEntry 1 }

cgspProfileVariant OBJECT-TYPE
    SYNTAX          CgspSS7Variant
    MAX-ACCESS      read-create
    STATUS          current
    DESCRIPTION
        "The SS7 variant used to format data specified in this
        profile."
    ::= { cgspProfileTableEntry 2 }

cgspProfileMtp2BundleTimer OBJECT-TYPE
    SYNTAX          Integer32 (0..0 | 5..10000)
    MAX-ACCESS      read-create
    STATUS          current
    DESCRIPTION
        "Bundle timer value.  This value is used to control
        the bundling of SS7 packets as they are transported
        within the device.  The value of zero indicates that
        MTP3 packets will not be bundled for transmission
        as they arrival for transmission at the MTP2 layer.
        A non-zero value specifies the maximum delay time
        used to collect MTP3 packets before they are
        transmitted by the MTP2 layer."
    ::= { cgspProfileTableEntry 3 }

cgspProfileMtp2SendQueueDepth OBJECT-TYPE
    SYNTAX          Integer32 (25..32000)
    MAX-ACCESS      read-create
    STATUS          current
    DESCRIPTION
        "The maximum Queue depth allowed per link for
        MTP2 waiting to be transmitted."
    ::= { cgspProfileTableEntry 4 }

cgspProfileRowStatus OBJECT-TYPE
    SYNTAX          RowStatus
    MAX-ACCESS      read-create
    STATUS          current
    DESCRIPTION
        "The object is used by a management station to
        create or delete the row entry in cgspProfileTable
        following the RowStatus textual convention."
    ::= { cgspProfileTableEntry 5 }


-- *************************************************************
-- *                                                           *
-- * Profile Timer Table                                       *
-- *                                                           *
-- *************************************************************

cgspProfileTimerTable OBJECT-TYPE
    SYNTAX          SEQUENCE OF CgspProfileTimerTableEntry
    MAX-ACCESS      not-accessible
    STATUS          current
    DESCRIPTION
        "A table that contains a profile of timers used to
        configure SS7 links.  Entries are added to this table
        via cgspProfileTimerRowStatus in accordance with the
        RowStatus convention."
    ::= { cgspProfile 2 }

cgspProfileTimerTableEntry OBJECT-TYPE
    SYNTAX          CgspProfileTimerTableEntry
    MAX-ACCESS      not-accessible
    STATUS          current
    DESCRIPTION
        "A list of ProfileTimer attributes.  Profiles are
        used to specify common timer configuration options
        for SS7 links without customizing each link.
        A profile is created with the specified values
        using this table and the cgspProfileTable
        Table.  The common values are applied to all
        links in a linkset by specifying the
        cgspLinksetProfileName on the linkset."
    INDEX           {
                        cgspInstNetwork,
                        cgspProfileTimerNumber
                    }
    ::= { cgspProfileTimerTable 1 }

CgspProfileTimerTableEntry ::= SEQUENCE {
        cgspProfileTimerNumber    CgspTimerNumbers,
        cgspProfileTimerValue     CgspTimerValue,
        cgspProfileTimerRowStatus RowStatus
}

cgspProfileTimerNumber OBJECT-TYPE
    SYNTAX          CgspTimerNumbers
    MAX-ACCESS      not-accessible
    STATUS          current
    DESCRIPTION
        "Index into table containing timer information."
    ::= { cgspProfileTimerTableEntry 1 }

cgspProfileTimerValue OBJECT-TYPE
    SYNTAX          CgspTimerValue
    UNITS           "milliseconds"
    MAX-ACCESS      read-create
    STATUS          current
    DESCRIPTION
        "Value of timer selected by cgspProfileTimerNumber object."
    ::= { cgspProfileTimerTableEntry 2 }

cgspProfileTimerRowStatus OBJECT-TYPE
    SYNTAX          RowStatus
    MAX-ACCESS      read-create
    STATUS          current
    DESCRIPTION
        "The object is used by a management station to
        create or delete the row entry in cgspProfileTimerTable
        following the RowStatus textual convention."
    ::= { cgspProfileTimerTableEntry 3 }


-- *************************************************************
-- *                                                           *
-- * Instance Table                                            *
-- *                                                           *
-- *************************************************************

cgspInstanceTable OBJECT-TYPE
    SYNTAX          SEQUENCE OF CgspInstanceTableEntry
    MAX-ACCESS      not-accessible
    STATUS          current
    DESCRIPTION
        "A table that contains the instances of signalling
        points.  Entries are added to this table via
        cgspInstRowStatus in accordance with the RowStatus
        convention."
    ::= { cgspInstance 1 }

cgspInstanceTableEntry OBJECT-TYPE
    SYNTAX          CgspInstanceTableEntry
    MAX-ACCESS      not-accessible
    STATUS          current
    DESCRIPTION
        "A list of instance attributes."
    INDEX           { cgspInstNetwork }
    ::= { cgspInstanceTable 1 }

CgspInstanceTableEntry ::= SEQUENCE {
        cgspInstNetwork                 CItpTcNetworkName,
        cgspInstNetworkIndicator        CItpTcNetworkIndicator,
        cgspInstVariant                 CgspSS7Variant,
        cgspInstDisplayName             SnmpAdminString,
        cgspInstDescription             SnmpAdminString,
        cgspInstTFR                     TruthValue,
        cgspInstCongestionsLevels       TruthValue,
        cgspInstFastRestart             TruthValue,
        cgspInstDistSccpUnseq           TruthValue,
        cgspInstSummaryRoutingException TruthValue,
        cgspInstNumber                  CItpTcInstanceNumber,
        cgspInstRouteTableName          CItpTcRouteTableName,
        cgspInstRowStatus               RowStatus,
        cgspInstSccpWrrOpcShift         Unsigned32,
        cgspInstSccpWrrOption           CItpTcSccpWrrOption
}

cgspInstNetwork OBJECT-TYPE
    SYNTAX          CItpTcNetworkName
    MAX-ACCESS      not-accessible
    STATUS          current
    DESCRIPTION
        "The network name is used to indicate the network
        in which this signalling point is participating.
        One or more instances of signalling points can
        exist in the same physical device.  This identifier
        will be used to correlate instances of signalling
        points by network.
        When multiple instance support is not enabled the
        network name will default to the null string.

        An octet string specified by an administrator that
        must be in human-readable form.  The names must conform
        to the allowed characters that can be specified via
        Command Line Interface(CLI).  The names cannot contain
        control character and should not contain leading or
        trailing white space."
    ::= { cgspInstanceTableEntry 1 }

cgspInstNetworkIndicator OBJECT-TYPE
    SYNTAX          CItpTcNetworkIndicator
    MAX-ACCESS      read-create
    STATUS          current
    DESCRIPTION
        "The Network Indicator for this Signalling point instance."
    ::= { cgspInstanceTableEntry 2 }

cgspInstVariant OBJECT-TYPE
    SYNTAX          CgspSS7Variant
    MAX-ACCESS      read-create
    STATUS          current
    DESCRIPTION
        "The SS7 variant used to format data used by this
        instance."
    ::= { cgspInstanceTableEntry 3 }

cgspInstDisplayName OBJECT-TYPE
    SYNTAX          SnmpAdminString (SIZE  (0..30))
    MAX-ACCESS      read-create
    STATUS          current
    DESCRIPTION
        "A short identifier for the Signalling point.
        This value can be set by system administrator
        or defaults to the local point code formatted
        as an ASCII string."
    ::= { cgspInstanceTableEntry 4 }

cgspInstDescription OBJECT-TYPE
    SYNTAX          SnmpAdminString (SIZE  (0..254))
    MAX-ACCESS      read-create
    STATUS          current
    DESCRIPTION
        "A textual description for the Signalling point."
    ::= { cgspInstanceTableEntry 5 }

cgspInstTFR OBJECT-TYPE
    SYNTAX          TruthValue
    MAX-ACCESS      read-create
    STATUS          current
    DESCRIPTION
        "Allow transfer restricted messages.
        'true'  TFR are allowed.
        'false' TFR are disabled."
    DEFVAL          { false }
    ::= { cgspInstanceTableEntry 6 }

cgspInstCongestionsLevels OBJECT-TYPE
    SYNTAX          TruthValue
    MAX-ACCESS      read-create
    STATUS          current
    DESCRIPTION
        "Allow multiple congestion levels.
        'true'  multiple congestion levels are allowed.
        'false' multiple congestion levels are disabled."
    DEFVAL          { false }
    ::= { cgspInstanceTableEntry 7 }

cgspInstFastRestart OBJECT-TYPE
    SYNTAX          TruthValue
    MAX-ACCESS      read-create
    STATUS          current
    DESCRIPTION
        "The support for fast restarts as follows.
        'true'  fast restart is enabled.
        'false' fast restart is disabled."
    DEFVAL          { false }
    ::= { cgspInstanceTableEntry 8 }

cgspInstDistSccpUnseq OBJECT-TYPE
    SYNTAX          TruthValue
    MAX-ACCESS      read-create
    STATUS          current
    DESCRIPTION
        "Evenly distribute Class 0 SCCP messages as follows.
        'true'   Evenly distribute 0 SCCP messages is enabled.
        'false'  Evenly distribute 0 SCCP messages is disabled."
    DEFVAL          { false }
    ::= { cgspInstanceTableEntry 9 }

cgspInstSummaryRoutingException OBJECT-TYPE
    SYNTAX          TruthValue
    MAX-ACCESS      read-create
    STATUS          current
    DESCRIPTION
        "This object is used to control the usage of the summary
        route when both a summary route (or ANSI cluster route)
        and a full point-code route (within that summary) are
        configured.  The object is used to indicate whether
        the summary route is to be used when the full
        point-code destination is inaccessible as follows.
         'true'   Use summary routing.
         'false'  Do not use summary routing."
    DEFVAL          { true }
    ::= { cgspInstanceTableEntry 10 }

cgspInstNumber OBJECT-TYPE
    SYNTAX          CItpTcInstanceNumber
    MAX-ACCESS      read-only
    STATUS          current
    DESCRIPTION
        "A unique Identifier assigned to each instance."
    ::= { cgspInstanceTableEntry 11 }

cgspInstRouteTableName OBJECT-TYPE
    SYNTAX          CItpTcRouteTableName
    MAX-ACCESS      read-create
    STATUS          current
    DESCRIPTION
        "The routing table for Signalling network management
        messages."
    REFERENCE
        "ITU Q.704 Signalling network functions and messages,
            section 14.2.1."
    ::= { cgspInstanceTableEntry 12 }

cgspInstRowStatus OBJECT-TYPE
    SYNTAX          RowStatus
    MAX-ACCESS      read-create
    STATUS          current
    DESCRIPTION
        "The object is used by a management station to
        create or delete the row entry in cgspInstanceTable
        following the RowStatus textual convention."
    ::= { cgspInstanceTableEntry 13 }

cgspInstSccpWrrOpcShift OBJECT-TYPE
    SYNTAX          Unsigned32 (0..8)
    MAX-ACCESS      read-create
    STATUS          current
    DESCRIPTION
        "This object indicates the shift amount for the
        OPC bits in SCCP class1 WRR(Weighted round robin).
        The range depends on the variant as follows.
        The ITU range is 0-2
        The ANSI range is 0-8
        The CHINA range is 0-2
        The JAPAN NTT range is 0-2
        The JAPAN TTC range is 0-2"
    ::= { cgspInstanceTableEntry 14 }

cgspInstSccpWrrOption OBJECT-TYPE
    SYNTAX          CItpTcSccpWrrOption
    MAX-ACCESS      read-create
    STATUS          current
    DESCRIPTION
        "This object indicate the options for calculate SCCP
        class 1 traffic loadshare under WRR"
    ::= { cgspInstanceTableEntry 15 }


-- *************************************************************
-- *                                                           *
-- * Instance Timer Table                                      *
-- *                                                           *
-- *************************************************************

cgspInstTimerTable OBJECT-TYPE
    SYNTAX          SEQUENCE OF CgspInstTimerTableEntry
    MAX-ACCESS      not-accessible
    STATUS          current
    DESCRIPTION
        "A table that contains the timer used to configure
        an instances of signalling points.  Entries are
        added to this table via cgspInstTimerRowStatus in
        accordance with the RowStatus convention."
    ::= { cgspInstance 2 }

cgspInstTimerTableEntry OBJECT-TYPE
    SYNTAX          CgspInstTimerTableEntry
    MAX-ACCESS      not-accessible
    STATUS          current
    DESCRIPTION
        "This table is used to configure all MTP3 timer
        values that apply to linksets and links.  The
        values apply to all linkset and links defined to
        this signalling point(instances)."
    INDEX           {
                        cgspInstNetwork,
                        cgspInstTimerNumber
                    }
    ::= { cgspInstTimerTable 1 }

CgspInstTimerTableEntry ::= SEQUENCE {
        cgspInstTimerNumber    CgspTimerNumbers,
        cgspInstTimerValue     CgspTimerValue,
        cgspInstTimerRowStatus RowStatus
}

cgspInstTimerNumber OBJECT-TYPE
    SYNTAX          CgspTimerNumbers
    MAX-ACCESS      not-accessible
    STATUS          current
    DESCRIPTION
        "Index into table containing timer information."
    ::= { cgspInstTimerTableEntry 1 }

cgspInstTimerValue OBJECT-TYPE
    SYNTAX          CgspTimerValue
    UNITS           "milliseconds"
    MAX-ACCESS      read-create
    STATUS          current
    DESCRIPTION
        "Value of timer selected by cgspInstTimerNumber object."
    ::= { cgspInstTimerTableEntry 2 }

cgspInstTimerRowStatus OBJECT-TYPE
    SYNTAX          RowStatus
    MAX-ACCESS      read-create
    STATUS          current
    DESCRIPTION
        "The object is used by a management station to
        create or delete the row entry in cgspInstTimerTable
        following the RowStatus textual convention."
    ::= { cgspInstTimerTableEntry 3 }


-- *************************************************************
-- *                                                           *
-- * Instance UPU Table                                        *
-- *                                                           *
-- *************************************************************

cgspInstUPUTable OBJECT-TYPE
    SYNTAX          SEQUENCE OF CgspInstUPUTableEntry
    MAX-ACCESS      not-accessible
    STATUS          current
    DESCRIPTION
        "The Instance UPU table contains information about the
        number of UPU MSUs transmitted and received for the
        specific user part(represented by service indicator)
        and signalling point instance. The user part is
        primarily represented with the possible service
        indicator.  This table provides the granularity of
        information required by Q752 table 5.6 and 5.7."
    ::= { cgspInstance 3 }

cgspInstUPUTableEntry OBJECT-TYPE
    SYNTAX          CgspInstUPUTableEntry
    MAX-ACCESS      not-accessible
    STATUS          current
    DESCRIPTION
        "Each table entry represent the UPU MSU statistics
        for a specific user part and signalling point
        instance."
    INDEX           {
                        cgspInstNetwork,
                        cgspMtp3SI
                    }
    ::= { cgspInstUPUTable 1 }

CgspInstUPUTableEntry ::= SEQUENCE {
        cgspMtp3SI               CItpTcServiceIndicator,
        cgspInstSIUPUReceived    Counter32,
        cgspInstSIUPUTransmitted Counter32,
        cgspInstUserPartDisplay  CgspDisplayInstanceUserPart
}

cgspMtp3SI OBJECT-TYPE
    SYNTAX          CItpTcServiceIndicator
    MAX-ACCESS      not-accessible
    STATUS          current
    DESCRIPTION
        "The service indicator."
    ::= { cgspInstUPUTableEntry 1 }

cgspInstSIUPUReceived OBJECT-TYPE
    SYNTAX          Counter32
    UNITS           "MSUs"
    MAX-ACCESS      read-only
    STATUS          current
    DESCRIPTION
        "The number of UPU MSUs that were received for the
        associated user part(service indicator) and
        and signalling point instance Q752/5.7."
    REFERENCE
        "ANSI GR-82-CORE 6.4.2 System Total Measurements Item 33
            measurements received from remote Signalling point."
    ::= { cgspInstUPUTableEntry 2 }

cgspInstSIUPUTransmitted OBJECT-TYPE
    SYNTAX          Counter32
    UNITS           "MSUs"
    MAX-ACCESS      read-only
    STATUS          current
    DESCRIPTION
        "The number of UPU MSUs that were transmitted for the
        associated user part(service indicator) and
        and signalling point instance."
    REFERENCE
        "ANSI GR-82-CORE 6.4.2 System Total Measurements Item 33."
    ::= { cgspInstUPUTableEntry 3 }

cgspInstUserPartDisplay OBJECT-TYPE
    SYNTAX          CgspDisplayInstanceUserPart
    MAX-ACCESS      read-only
    STATUS          current
    DESCRIPTION
        "The associated instance name and user part information
        formatted for display."
    ::= { cgspInstUPUTableEntry 4 }


-- *************************************************************
-- *                                                           *
-- * Point Code Table                                          *
-- *                                                           *
-- *************************************************************

cgspPointCodeTable OBJECT-TYPE
    SYNTAX          SEQUENCE OF CgspPointCodeTableEntry
    MAX-ACCESS      not-accessible
    STATUS          current
    DESCRIPTION
        "A table that contains a list of point code defined for the
        Signalling point defined by this instance. Entries are
        added to this table via cgspPointCodeRowStatus in
        accordance with the RowStatus convention."
    ::= { cgspPointCode 1 }

cgspPointCodeTableEntry OBJECT-TYPE
    SYNTAX          CgspPointCodeTableEntry
    MAX-ACCESS      not-accessible
    STATUS          current
    DESCRIPTION
        "A list of Point codes for a signalling point
        defined by an instance."
    INDEX           {
                        cgspInstNetwork,
                        cgspPointCodeNi,
                        cgspPointCodeBin
                    }
    ::= { cgspPointCodeTable 1 }

CgspPointCodeTableEntry ::= SEQUENCE {
        cgspPointCodeNi        CItpTcNetworkIndicator,
        cgspPointCodeBin       CItpTcPointCode,
        cgspPointCodeType      CItpTcPointCodeType,
        cgspPointCodeDisplay   CItpTcDisplayPC,
        cgspPointCodeRowStatus RowStatus
}

cgspPointCodeNi OBJECT-TYPE
    SYNTAX          CItpTcNetworkIndicator
    MAX-ACCESS      not-accessible
    STATUS          current
    DESCRIPTION
        "The network Indicator for this pointcode."
    ::= { cgspPointCodeTableEntry 1 }

cgspPointCodeBin OBJECT-TYPE
    SYNTAX          CItpTcPointCode
    MAX-ACCESS      not-accessible
    STATUS          current
    DESCRIPTION
        "The point code for this Signalling Point."
    ::= { cgspPointCodeTableEntry 2 }

cgspPointCodeType OBJECT-TYPE
    SYNTAX          CItpTcPointCodeType
    MAX-ACCESS      read-create
    STATUS          current
    DESCRIPTION
        "The function of this point code."
    ::= { cgspPointCodeTableEntry 3 }

cgspPointCodeDisplay OBJECT-TYPE
    SYNTAX          CItpTcDisplayPC
    MAX-ACCESS      read-only
    STATUS          current
    DESCRIPTION
        "The point code for this Signalling Point."
    ::= { cgspPointCodeTableEntry 4 }

cgspPointCodeRowStatus OBJECT-TYPE
    SYNTAX          RowStatus
    MAX-ACCESS      read-create
    STATUS          current
    DESCRIPTION
        "The object is used by a management station to create or
        delete the row entry in cgspPointCodeTable following
        the RowStatus textual convention."
    ::= { cgspPointCodeTableEntry 5 }


-- *************************************************************
-- *                                                           *
-- * Linkset Table                                             *
-- *                                                           *
-- *************************************************************

cgspLinksetTable OBJECT-TYPE
    SYNTAX          SEQUENCE OF CgspLinksetTableEntry
    MAX-ACCESS      not-accessible
    STATUS          current
    DESCRIPTION
        "A table of linksets for this Signalling Point
        defined by this instance."
    ::= { cgspLinkset 1 }

cgspLinksetTableEntry OBJECT-TYPE
    SYNTAX          CgspLinksetTableEntry
    MAX-ACCESS      not-accessible
    STATUS          current
    DESCRIPTION
        "A list of Signalling Point linkset attributes for
        Signalling Point define by this instance."
    INDEX           {
                        cgspInstNetwork,
                        cgspLinksetName
                    }
    ::= { cgspLinksetTable 1 }

CgspLinksetTableEntry ::= SEQUENCE {
        cgspLinksetName               CItpTcLinksetId,
        cgspLinksetSourcePointCode    CItpTcPointCode,
        cgspLinksetSourceDisplayPC    CItpTcDisplayPC,
        cgspLinksetAdjacentPointCode  CItpTcPointCode,
        cgspLinksetAdjacentDisplayPC  CItpTcDisplayPC,
        cgspLinksetState              INTEGER,
        cgspLinksetInboundAcl         CItpTcAclId,
        cgspLinksetOutboundAcl        CItpTcAclId,
        cgspLinksetAccountingMtp3     TruthValue,
        cgspLinksetAccountingGtt      TruthValue,
        cgspLinksetNumLinks           Unsigned32,
        cgspLinksetDurationInService  Counter32,
        cgspLinksetDurationOutService Counter32,
        cgspLinksetActPriority        Unsigned32,
        cgspLinksetDisplayName        SnmpAdminString,
        cgspLinksetDescription        SnmpAdminString,
        cgspLinksetRotateSlsEnable    TruthValue,
        cgspLinksetRotateSlsShift     Unsigned32,
        cgspLinksetProfileName        CgspProfileName,
        cgspLinksetAdjacentInst       CItpTcNetworkName,
        cgspLinksetRowStatus          RowStatus
}

cgspLinksetName OBJECT-TYPE
    SYNTAX          CItpTcLinksetId
    MAX-ACCESS      not-accessible
    STATUS          current
    DESCRIPTION
        "The name of the linkset."
    ::= { cgspLinksetTableEntry 1 }

cgspLinksetSourcePointCode OBJECT-TYPE
    SYNTAX          CItpTcPointCode
    MAX-ACCESS      read-create
    STATUS          current
    DESCRIPTION
        "The point code to which this linkset is connected."
    ::= { cgspLinksetTableEntry 2 }

cgspLinksetSourceDisplayPC OBJECT-TYPE
    SYNTAX          CItpTcDisplayPC
    MAX-ACCESS      read-only
    STATUS          current
    DESCRIPTION
        "The point code to which this linkset is connected."
    ::= { cgspLinksetTableEntry 3 }

cgspLinksetAdjacentPointCode OBJECT-TYPE
    SYNTAX          CItpTcPointCode
    MAX-ACCESS      read-create
    STATUS          current
    DESCRIPTION
        "The point code to which this linkset is connected."
    ::= { cgspLinksetTableEntry 4 }

cgspLinksetAdjacentDisplayPC OBJECT-TYPE
    SYNTAX          CItpTcDisplayPC
    MAX-ACCESS      read-only
    STATUS          current
    DESCRIPTION
        "The point code to which this linkset is connected."
    ::= { cgspLinksetTableEntry 5 }

cgspLinksetState OBJECT-TYPE
    SYNTAX          INTEGER  {
                        available(1),
                        shutdown(2),
                        unavailable(3)
                    }
    MAX-ACCESS      read-only
    STATUS          current
    DESCRIPTION
        "The list of possible linkset states.
        'available'  : Traffic may flow over this linkset
        'shutdown'   : This linkset has been forced to an
                       unavailable state by an administrative
                       action.
        'unavailable': The linkset is currently unable to support
                       traffic. Activation of this linkset will
                       occur as required by protocol."
    ::= { cgspLinksetTableEntry 6 }

cgspLinksetInboundAcl OBJECT-TYPE
    SYNTAX          CItpTcAclId
    MAX-ACCESS      read-create
    STATUS          current
    DESCRIPTION
        "Packets are filtered against this access control list
        before they are passed to the routing function.  A
        value of zero indicates that no access control list
        is present."
    ::= { cgspLinksetTableEntry 7 }

cgspLinksetOutboundAcl OBJECT-TYPE
    SYNTAX          CItpTcAclId
    MAX-ACCESS      read-create
    STATUS          current
    DESCRIPTION
        "Packets are filtered against this access control list
        after they have passed through the routing function.
        A value of zero indicates that no access control list
        is present."
    ::= { cgspLinksetTableEntry 8 }

cgspLinksetAccountingMtp3 OBJECT-TYPE
    SYNTAX          TruthValue
    MAX-ACCESS      read-create
    STATUS          current
    DESCRIPTION
        "This indicates if accounting for this linkset is
        enabled.

        'true'  Indicates that the accounting function is
                enabled for this linkset and is being
                accumulated in cgactMtp3Table.

        'false' Indicates that the accounting function is
                disabled."
    DEFVAL          { false }
    ::= { cgspLinksetTableEntry 9 }

cgspLinksetAccountingGtt OBJECT-TYPE
    SYNTAX          TruthValue
    MAX-ACCESS      read-create
    STATUS          current
    DESCRIPTION
        "This indicates if accounting for this linkset is
        enabled.

        'true'  Indicates that the accounting function is
                enabled for this linkset and is being
                accumulated in cgactMtp3Table.

        'false' Indicates that the accounting function is
                disabled."
    DEFVAL          { false }
    ::= { cgspLinksetTableEntry 10 }

cgspLinksetNumLinks OBJECT-TYPE
    SYNTAX          Unsigned32
    MAX-ACCESS      read-only
    STATUS          current
    DESCRIPTION
        "The number of links in this linkset."
    ::= { cgspLinksetTableEntry 11 }

cgspLinksetDurationInService OBJECT-TYPE
    SYNTAX          Counter32
    UNITS           "seconds"
    MAX-ACCESS      read-only
    STATUS          current
    DESCRIPTION
        "Time linkset was providing service related to
        Q752/Table 4.2."
    ::= { cgspLinksetTableEntry 12 }

cgspLinksetDurationOutService OBJECT-TYPE
    SYNTAX          Counter32
    UNITS           "seconds"
    MAX-ACCESS      read-only
    STATUS          current
    DESCRIPTION
        "Time linkset was Out-of-Service as required for
        Q752/Table 4.2."
    ::= { cgspLinksetTableEntry 13 }

cgspLinksetActPriority OBJECT-TYPE
    SYNTAX          Unsigned32 (0..255)
    MAX-ACCESS      read-create
    STATUS          current
    DESCRIPTION
        "Defines the activation priority for linksets.  The
        linksets with the lowest values will be activated
        first.  If two or more linksets share the same values
        they will be activated in the order they were defined."
    DEFVAL          { 0 }
    ::= { cgspLinksetTableEntry 14 }

cgspLinksetDisplayName OBJECT-TYPE
    SYNTAX          SnmpAdminString (SIZE  (0..30))
    MAX-ACCESS      read-create
    STATUS          current
    DESCRIPTION
        "A short identifier for each linkset.
        This value can be set by system administrator
        or defaults to the linkset name."
    ::= { cgspLinksetTableEntry 15 }

cgspLinksetDescription OBJECT-TYPE
    SYNTAX          SnmpAdminString (SIZE  (0..254))
    MAX-ACCESS      read-create
    STATUS          current
    DESCRIPTION
        "A textual description for the Signalling point."
    ::= { cgspLinksetTableEntry 16 }

cgspLinksetRotateSlsEnable OBJECT-TYPE
    SYNTAX          TruthValue
    MAX-ACCESS      read-create
    STATUS          current
    DESCRIPTION
        "This defines whether signalling link selector(SLS) will
        be rotated.  This option only applies to ANSI variant
        and will return false for all other variants.  By default
        SLS rotation is enable by default for ANSI linksets.  ANSI
        specifications state that SLS rotation should not be
        performed on C type linksets.  This object can be used to
        disable SLS rotation.

        'true'  Indicates that SLS rotation is enable for this
               linkset.

        'false' Indicates that SLS rotation is disable for this
               linkset."
    ::= { cgspLinksetTableEntry 17 }

cgspLinksetRotateSlsShift OBJECT-TYPE
    SYNTAX          Unsigned32 (0..3)
    MAX-ACCESS      read-create
    STATUS          current
    DESCRIPTION
        "This value used to shift the signalling link selector(SLS)
        when rotation is enabled.  This option only applies to
        ANSI variant and will return 0 all other variants."
    ::= { cgspLinksetTableEntry 18 }

cgspLinksetProfileName OBJECT-TYPE
    SYNTAX          CgspProfileName
    MAX-ACCESS      read-create
    STATUS          current
    DESCRIPTION
        "When specified this object indicates which profile will be
        used to establish defaults for common configuration
        values like MTP2 and MTP3 timers.  The null string is used
        to indicate that the linkset does not have a profile."
    ::= { cgspLinksetTableEntry 19 }

cgspLinksetAdjacentInst OBJECT-TYPE
    SYNTAX          CItpTcNetworkName
    MAX-ACCESS      read-only
    STATUS          current
    DESCRIPTION
        "When a linkset is used to carry traffic between
        different instances, this object contains the
        network name used as an index into the cgspInstanceTable
        table.  In all other cases the object will contain
        the same network name as the source signalling point."
    ::= { cgspLinksetTableEntry 20 }

cgspLinksetRowStatus OBJECT-TYPE
    SYNTAX          RowStatus
    MAX-ACCESS      read-create
    STATUS          current
    DESCRIPTION
        "The object is used by a management station to
        create or delete the row entry in cgspLinksetTable
        following the RowStatus textual convention."
    ::= { cgspLinksetTableEntry 21 }


-- *************************************************************
-- *                                                           *
-- * Linkset Timer Table                                       *
-- *                                                           *
-- *************************************************************

cgspLinksetTimerTable OBJECT-TYPE
    SYNTAX          SEQUENCE OF CgspLinksetTimerTableEntry
    MAX-ACCESS      not-accessible
    STATUS          current
    DESCRIPTION
        "A table that contains the timer used to configure timer
        values specific to a particular linkset.  Entries are added
        to this table via cgspLinksetTimerRowStatus in accordance
        with the RowStatus convention."
    ::= { cgspLinkset 2 }

cgspLinksetTimerTableEntry OBJECT-TYPE
    SYNTAX          CgspLinksetTimerTableEntry
    MAX-ACCESS      not-accessible
    STATUS          current
    DESCRIPTION
        "This table is used to configure all MTP3 timer
        values that apply to linksets and links.  The
        values apply to this linkset and links it c
        contains."
    INDEX           {
                        cgspInstNetwork,
                        cgspLinksetName,
                        cgspLinksetTimerNumber
                    }
    ::= { cgspLinksetTimerTable 1 }

CgspLinksetTimerTableEntry ::= SEQUENCE {
        cgspLinksetTimerNumber    CgspTimerNumbers,
        cgspLinksetTimerValue     CgspTimerValue,
        cgspLinksetTimerRowStatus RowStatus
}

cgspLinksetTimerNumber OBJECT-TYPE
    SYNTAX          CgspTimerNumbers
    MAX-ACCESS      not-accessible
    STATUS          current
    DESCRIPTION
        "Index into table containing timer information."
    ::= { cgspLinksetTimerTableEntry 1 }

cgspLinksetTimerValue OBJECT-TYPE
    SYNTAX          CgspTimerValue
    UNITS           "milliseconds"
    MAX-ACCESS      read-create
    STATUS          current
    DESCRIPTION
        "Value of timer selected by cgspLinksetTimerNumber object."
    ::= { cgspLinksetTimerTableEntry 2 }

cgspLinksetTimerRowStatus OBJECT-TYPE
    SYNTAX          RowStatus
    MAX-ACCESS      read-create
    STATUS          current
    DESCRIPTION
        "The object is used by a management station to
        create or delete the row entry in cgspLinksetTimerTable
        following the RowStatus textual convention."
    ::= { cgspLinksetTimerTableEntry 3 }


-- *************************************************************
-- *                                                           *
-- * GSP - Link Table                                          *
-- *                                                           *
-- *************************************************************

cgspLinkTable OBJECT-TYPE
    SYNTAX          SEQUENCE OF CgspLinkTableEntry
    MAX-ACCESS      not-accessible
    STATUS          current
    DESCRIPTION
        "A table of links for each Signalling Point."
    ::= { cgspLink 1 }

cgspLinkTableEntry OBJECT-TYPE
    SYNTAX          CgspLinkTableEntry
    MAX-ACCESS      not-accessible
    STATUS          current
    DESCRIPTION
        "A list of signalling point link attributes."
    INDEX           {
                        cgspInstNetwork,
                        cgspLinksetName,
                        cgspLinkSlc
                    }
    ::= { cgspLinkTable 1 }

CgspLinkTableEntry ::= SEQUENCE {
        cgspLinkSlc                  CItpTcLinkSLC,
        cgspLinkDescription          SnmpAdminString,
        cgspLinkState                INTEGER,
        cgspLinkReason               INTEGER,
        cgspLinkType                 CItpTcLinkType,
        cgspLinkifIndex              InterfaceIndexOrZero,
        cgspLinkSctpAssociation      Unsigned32,
        cgspLinkXmitQueueDepth       Gauge32,
        cgspLinkXmitQueueDepthHigh   Unsigned32,
        cgspLinkXmitQueueDepthHighRT TimeStamp,
        cgspLinkCongestionState      Unsigned32,
        cgspLinkCongestionAbate1     Unsigned32,
        cgspLinkCongestionAbate2     Unsigned32,
        cgspLinkCongestionAbate3     Unsigned32,
        cgspLinkCongestionOnset1     Unsigned32,
        cgspLinkCongestionOnset2     Unsigned32,
        cgspLinkCongestionOnset3     Unsigned32,
        cgspLinkSigLinkTest          TruthValue,
        cgspLinkQ752T1E1             Counter32,
        cgspLinkQ752T1E2             Counter32,
        cgspLinkQ752T1E3             Counter32,
        cgspLinkQ752T1E5             Counter32,
        cgspLinkQ752T1E7             Counter32,
        cgspLinkQ752T1E8             Counter32,
        cgspLinkQ752T1E9             Counter32,
        cgspLinkQ752T1E10            Counter32,
        cgspLinkQ752T1E11            Counter32,
        cgspLinkQ752T2E1             Counter32,
        cgspLinkQ752T2E5             Counter32,
        cgspLinkQ752T2E6             Counter32,
        cgspLinkQ752T2E7             Counter32,
        cgspLinkQ752T2E9             Counter32,
        cgspLinkQ752T2E10            Counter32,
        cgspLinkQ752T2E15            Counter32,
        cgspLinkQ752T2E16            Counter32,
        cgspLinkQ752T2E18            Counter32,
        cgspLinkQ752T3E1             Counter32,
        cgspLinkQ752T3E2Bytes        Counter32,
        cgspLinkQ752T3E2Packets      Counter32,
        cgspLinkQ752T3E3             Counter32,
        cgspLinkQ752T3E4             Counter32,
        cgspLinkQ752T3E5             Counter32,
        cgspLinkQ752T3E6             Counter32,
        cgspLinkQ752T3E7             Counter32,
        cgspLinkQ752T3E10L1          Counter32,
        cgspLinkQ752T3E10L2          Counter32,
        cgspLinkQ752T3E10L3          Counter32,
        cgspLinkQ752T3E11L1          Counter32,
        cgspLinkQ752T3E11L2          Counter32,
        cgspLinkQ752T3E11L3          Counter32,
        cgspLinkLocalPeerPort        InetPortNumber,
        cgspLinkRemotePeerPort       InetPortNumber,
        cgspLinkQosClass             CItpTcQos,
        cgspLinkDisplayName          SnmpAdminString,
        cgspLinkDroppedPkts          Counter32,
        cgspLinkTransmittedLSSUs     Counter32,
        cgspLinkReceivedLSSUs        Counter32,
        cgspLinkProtocolDetails      BITS,
        cgspLinkLsacState            INTEGER,
        cgspLinkTsrcState            INTEGER,
        cgspLinkTcocState            INTEGER,
        cgspLinkTcocLocalBSNT        CgspSequenceNumber,
        cgspLinkTcocRemoteBSNT       CgspSequenceNumber,
        cgspLinkTcbcState            INTEGER,
        cgspLinkReceivedSIBs         Counter32,
        cgspLinkTransmittedSIBs      Counter32,
        cgspLinkMtp2T01Counts        Counter32,
        cgspLinkMtp2T02Counts        Counter32,
        cgspLinkMtp2T03Counts        Counter32,
        cgspLinkMtp2T04Counts        Counter32,
        cgspLinkMtp2T05Counts        Counter32,
        cgspLinkMtp2T06Counts        Counter32,
        cgspLinkMtp2T07Counts        Counter32,
        cgspLinkOMAERMCounts         Counter32,
        cgspLinkOMAERMFailCounts     Counter32,
        cgspLinkOMSURMCounts         Counter32,
        cgspLinkOMSURMFailCounts     Counter32,
        cgspLinkPlanCapacityRcvd     CgspLinkCapacity,
        cgspLinkUtilThresholdRcvd    CgspPercentThreshold,
        cgspLinkUtilizationRcvd      CgspLinkUtilization,
        cgspLinkUtilStateRcvd        CgspLinkUtilizationState,
        cgspLinkL2BytesRcvd          Counter32,
        cgspLinkPlanCapacitySent     CgspLinkCapacity,
        cgspLinkUtilThresholdSent    CgspPercentThreshold,
        cgspLinkUtilizationSent      CgspLinkUtilization,
        cgspLinkUtilStateSent        CgspLinkUtilizationState,
        cgspLinkL2BytesSent          Counter32,
        cgspLinkTestResult           CgspLinkTestResults,
        cgspLinkRowStatus            RowStatus,
        cgspLinkSctpAssociationId    Unsigned32,
        cgspLinkQ752T1E12            Counter32,
        cgspLinkQ752T1E12Errors      Counter32,
        cgspLinkQ752T2E11            Counter32,
        cgspLinkQ752T2E17            Counter32,
        cgspLinkQ752T2E19            Counter32,
        cgspLinkRxCongestionState    Unsigned32
}

cgspLinkSlc OBJECT-TYPE
    SYNTAX          CItpTcLinkSLC
    MAX-ACCESS      not-accessible
    STATUS          current
    DESCRIPTION
        "The Signalling Link Code for this link."
    REFERENCE
        "ITU Q.704 Signalling network functions and messages.
            ANSI T1.111 Telecommunications - Signalling system
            No. 7 (SS7)-Message Transfer Part (MTP)."
    ::= { cgspLinkTableEntry 1 }

cgspLinkDescription OBJECT-TYPE
    SYNTAX          SnmpAdminString (SIZE  (0..254))
    MAX-ACCESS      read-create
    STATUS          current
    DESCRIPTION
        "A textual description for this link."
    ::= { cgspLinkTableEntry 2 }

cgspLinkState OBJECT-TYPE
    SYNTAX          INTEGER  {
                        available(1),
                        failed(2),
                        shutdown(3),
                        unavailable(4)
                    }
    MAX-ACCESS      read-only
    STATUS          current
    DESCRIPTION
        "The list of possible links states.
        'available'  : Traffic may flow over this linkset
        'failed'     : Traffic management has detected a failure
                       that prevents activating this linkset.
        'shutdown'   : This linkset has been forced to an
                       unavailable state by an administrative
                       action.
        'unavailable': The linkset is currently unable to support
                       traffic. Activation of this linkset will
                       occur as required by protocol."
    ::= { cgspLinkTableEntry 3 }

cgspLinkReason OBJECT-TYPE
    SYNTAX          INTEGER  {
                        unknown(0),
                        changeOverInProgress(1),
                        mgmtDisconnectRequest(2),
                        linkAlignmentLost(3),
                        connectionLost(4),
                        localDisconnect(5),
                        remoteDisconnect(6),
                        suermFailure(7),
                        t1Timeout(8),
                        t2Timeout(9),
                        t3Timeout(10),
                        t6Timeout(11),
                        t7Timeout(12),
                        provingFailure(13),
                        protocolErrorBsn(14),
                        protocolErrorFib(15),
                        protocolErrorSin(16),
                        protocolErrorLssu(17),
                        peerNotReady(18),
                        communicationLost(19),
                        noListenPosted(20),
                        bufferNotAvailable(21),
                        cardRemoved(22),
                        cardInserted(23),
                        falseLinkCongestion(24),
                        configDownload(25),
                        localInhibit(26),
                        localUninhibit(27),
                        remoteInhibit(28),
                        remoteUninhibit(29),
                        localBlocked(30),
                        localUnBlocked(31),
                        remoteBlocked(32),
                        remoteUnblocked(33),
                        linkRestored(34),
                        linkTestFailure(35)
                    }
    MAX-ACCESS      read-only
    STATUS          current
    DESCRIPTION
        "This object provides additional information on the source
        of a link failure.  This object will contain the last reason
        that caused the link to fail.
          'unknown' : Link has failed do to an undetermined cause.
          'changeOverInProgress' : Change over in progress.
          'mgmtDisconnectRequest' : Management disconnect
               request.
          'linkAlignmentLost' : Link alignment lost.
          'connectionLost' : Link connection lost.
          'localDisconnect' : Local Disconnect.
          'remoteDisconnect' : Remote Disconnect.
          'suermFailure' :   Signal unit error rate monitor
               failure.
          't1Timeout' : T1 timeout no FISU received.
          't2Timeout' : T2 timeout no SIO received.
          't3Timeout' : T3 timeout no SIN received.
          't6Timeout' : T6 timeout excessive congestion.
          't7Timeout' : T7 timeout excessive acknowledgement
               delay.
          'provingFailure' : Link proving failure.
          'protocolError-BSN' : Abnormal BSN received.
          'protocolError-FIB' : Abnormal FIB received.
          'protocolError-SIN' : Abnormal SIB received.
          'protocolError-LSSU' : Abnormal LSSU received.
          'peerNotReady' : Peer not ready.
          'communicationLost' : Communication lost.
          'noListenPosted' : No Listen posted.
          'bufferNotAvailable' : Unable to allocate buffer.
          'cardRemoved'  : Link card removed.
          'cardInserted' : Link card Inserted.
          'falseLinkCongestion' : false link congestion.
          'configDownload' : Configuration downloading.
          'localInhibit'   : Local request to inhibit link.
          'localUninhibit' : Local request to uninhibit link.
          'remoteInhibit'  : Remote request to inhibit link.
          'remoteUninhibit': Local request to uninhibit link.
          'localBlocked'   : Local Processor outage.
          'localUnBlocked' : Local Processor recovery.
          'remoteBlocked'  : Remote Processor outage.
          'remoteUnblocked': Remote Processor recovery.
          'linkRestored'   : Link restored.
          'linkTestFailure': Signalling Link Test failure.'"
    ::= { cgspLinkTableEntry 4 }

cgspLinkType OBJECT-TYPE
    SYNTAX          CItpTcLinkType
    MAX-ACCESS      read-create
    STATUS          current
    DESCRIPTION
        "The link type."
    REFERENCE       "For SCTP see RFC 2960."
    ::= { cgspLinkTableEntry 5 }

cgspLinkifIndex OBJECT-TYPE
    SYNTAX          InterfaceIndexOrZero
    MAX-ACCESS      read-create
    STATUS          current
    DESCRIPTION
        "If the link type specified by cgspLinkType is serial
        or high speed Link, this is the ifIndex specified in
        IF-MIB, otherwise no significance is to be placed on
        this value."
    REFERENCE       "RFC1213.txt"
    ::= { cgspLinkTableEntry 6 }

cgspLinkSctpAssociation OBJECT-TYPE
    SYNTAX          Unsigned32 (0..65535)
    MAX-ACCESS      read-only
    STATUS          deprecated
    DESCRIPTION
        "Association Identifiers can be greater than 65,535.
        This object has been replaced by
        cgspLinkSctpAssociationId."
    ::= { cgspLinkTableEntry 7 }

cgspLinkXmitQueueDepth OBJECT-TYPE
    SYNTAX          Gauge32
    MAX-ACCESS      read-only
    STATUS          current
    DESCRIPTION
        "Number of packets waiting to be sent over this link."
    ::= { cgspLinkTableEntry 8 }

cgspLinkXmitQueueDepthHigh OBJECT-TYPE
    SYNTAX          Unsigned32
    MAX-ACCESS      read-create
    STATUS          current
    DESCRIPTION
        "This is the maximum number of packets waiting
        to be sent over this link since the last time this
        value was reset as indicated by
        cgspLinkXmitQueueDepthHighRT.
        Resetting this object is achieved by setting this
        object to 0.  Attempting to set this object to any
        other value will result in a wrongValue (SNMPv2c,
        SNMPv3) or badValue (SNMPv1)."
    ::= { cgspLinkTableEntry 9 }

cgspLinkXmitQueueDepthHighRT OBJECT-TYPE
    SYNTAX          TimeStamp
    MAX-ACCESS      read-only
    STATUS          current
    DESCRIPTION
        "This indicates when cgspLinkXmitQueueDepthHigh
        was last set to 0."
    ::= { cgspLinkTableEntry 10 }

cgspLinkCongestionState OBJECT-TYPE
    SYNTAX          Unsigned32 (0..3)
    MAX-ACCESS      read-only
    STATUS          current
    DESCRIPTION
        "The Signalling link congestion status of this link. 0
        is the least congestion level, 3 is the highest
        congestion level."
    REFERENCE
        "ITU Q.704 Signalling network functions and messages.
            ANSI T1.111 Telecommunications - Signalling system
            No. 7 (SS7)-Signalling network functions and messages
            2.3.5.2."
    ::= { cgspLinkTableEntry 11 }

cgspLinkCongestionAbate1 OBJECT-TYPE
    SYNTAX          Unsigned32 (0..65535)
    MAX-ACCESS      read-create
    STATUS          current
    DESCRIPTION
        "Threshold used to abate congestion level 1."
    ::= { cgspLinkTableEntry 12 }

cgspLinkCongestionAbate2 OBJECT-TYPE
    SYNTAX          Unsigned32 (0..65535)
    MAX-ACCESS      read-create
    STATUS          current
    DESCRIPTION
        "Threshold used to abate congestion level 2."
    ::= { cgspLinkTableEntry 13 }

cgspLinkCongestionAbate3 OBJECT-TYPE
    SYNTAX          Unsigned32 (0..65535)
    MAX-ACCESS      read-create
    STATUS          current
    DESCRIPTION
        "Threshold used to abate congestion level 3."
    ::= { cgspLinkTableEntry 14 }

cgspLinkCongestionOnset1 OBJECT-TYPE
    SYNTAX          Unsigned32 (0..65535)
    MAX-ACCESS      read-create
    STATUS          current
    DESCRIPTION
        "Threshold used to mark onset of congestion level 1."
    ::= { cgspLinkTableEntry 15 }

cgspLinkCongestionOnset2 OBJECT-TYPE
    SYNTAX          Unsigned32 (0..65535)
    MAX-ACCESS      read-create
    STATUS          current
    DESCRIPTION
        "Threshold used to mark onset of congestion level 2."
    ::= { cgspLinkTableEntry 16 }

cgspLinkCongestionOnset3 OBJECT-TYPE
    SYNTAX          Unsigned32 (0..65535)
    MAX-ACCESS      read-create
    STATUS          current
    DESCRIPTION
        "Threshold used to mark onset of congestion level 3."
    ::= { cgspLinkTableEntry 17 }

cgspLinkSigLinkTest OBJECT-TYPE
    SYNTAX          TruthValue
    MAX-ACCESS      read-create
    STATUS          current
    DESCRIPTION
        "Indicated if Signalling link test is enabled on this
        link.

        true  : Signalling link test is enabled.
        false : Signalling link test not enabled."
    DEFVAL          { true }
    ::= { cgspLinkTableEntry 18 }

cgspLinkQ752T1E1 OBJECT-TYPE
    SYNTAX          Counter32
    UNITS           "seconds"
    MAX-ACCESS      read-only
    STATUS          current
    DESCRIPTION
        "Duration of link in the In-Service state Q752/1.1."
    REFERENCE
        "ANSI GR-82-CORE 6.4.4 Link Measurements Item 23-24."
    ::= { cgspLinkTableEntry 19 }

cgspLinkQ752T1E2 OBJECT-TYPE
    SYNTAX          Counter32
    MAX-ACCESS      read-only
    STATUS          current
    DESCRIPTION
        "Count of Signalling Link failures - All reasons Q752/1.2."
    REFERENCE       "ANSI GR-82-CORE 6.4.4 Link Measurements Item 29."
    ::= { cgspLinkTableEntry 20 }

cgspLinkQ752T1E3 OBJECT-TYPE
    SYNTAX          Counter32
    UNITS           "occurrences"
    MAX-ACCESS      read-only
    STATUS          current
    DESCRIPTION
        "Count of Signalling Link failures - Abnormal FIBR/BSNR
        Q752/1.3"
    ::= { cgspLinkTableEntry 21 }

cgspLinkQ752T1E5 OBJECT-TYPE
    SYNTAX          Counter32
    UNITS           "occurrences"
    MAX-ACCESS      read-only
    STATUS          current
    DESCRIPTION
        "Count of Signalling Link failures - Excessive error rate
        Q752/1.5."
    ::= { cgspLinkTableEntry 22 }

cgspLinkQ752T1E7 OBJECT-TYPE
    SYNTAX          Counter32
    UNITS           "occurrences"
    MAX-ACCESS      read-only
    STATUS          current
    DESCRIPTION
        "Count of alignment or proving errors Q752/1.7."
    ::= { cgspLinkTableEntry 23 }

cgspLinkQ752T1E8 OBJECT-TYPE
    SYNTAX          Counter32
    UNITS           "occurrences"
    MAX-ACCESS      read-only
    STATUS          current
    DESCRIPTION
        "Count of signal units received in error Q752/1.8."
    REFERENCE       "ANSI GR-82-CORE 6.4.4 Link Measurements Item 33."
    ::= { cgspLinkTableEntry 24 }

cgspLinkQ752T1E9 OBJECT-TYPE
    SYNTAX          Counter32
    UNITS           "negative acknowledgements"
    MAX-ACCESS      read-only
    STATUS          current
    DESCRIPTION
        "Count of negative acknowledgements received Q752/1.9."
    REFERENCE       "ANSI GR-82-CORE 6.4.4 Link Measurements Item 34."
    ::= { cgspLinkTableEntry 25 }

cgspLinkQ752T1E10 OBJECT-TYPE
    SYNTAX          Counter32
    UNITS           "occurrences"
    MAX-ACCESS      read-only
    STATUS          current
    DESCRIPTION
        "Count of 'local automatic changeover' events
        Q752/1.10."
    REFERENCE       "ANSI GR-82-CORE 6.4.4 Link Measurements Item 25."
    ::= { cgspLinkTableEntry 26 }

cgspLinkQ752T1E11 OBJECT-TYPE
    SYNTAX          Counter32
    UNITS           "occurrences"
    MAX-ACCESS      read-only
    STATUS          current
    DESCRIPTION
        "Count of 'local automatic changeback' events Q752/1.11."
    ::= { cgspLinkTableEntry 27 }

-- Q752.12 Signalling Link Restoration  The standard only requires
-- that an event be issued when this occurs.

cgspLinkQ752T2E1 OBJECT-TYPE
    SYNTAX          Counter32
    UNITS           "seconds"
    MAX-ACCESS      read-only
    STATUS          current
    DESCRIPTION
        "Duration of Signalling Link unavailable(for any reason)
        Q752/2.1."
    REFERENCE       "ANSI GR-82-CORE 6.4.4 Link Measurements Item 30."
    ::= { cgspLinkTableEntry 28 }

-- Q752/2.2 - Q752/2.4 deleted

cgspLinkQ752T2E5 OBJECT-TYPE
    SYNTAX          Counter32
    UNITS           "seconds"
    MAX-ACCESS      read-only
    STATUS          current
    DESCRIPTION
        "Duration of Signalling Link unavailable due to local
        management actions Q752/2.5."
    ::= { cgspLinkTableEntry 29 }

cgspLinkQ752T2E6 OBJECT-TYPE
    SYNTAX          Counter32
    UNITS           "seconds"
    MAX-ACCESS      read-only
    STATUS          current
    DESCRIPTION
        "Duration of Signalling Link unavailable due to remote
        management actions Q752/2.6."
    ::= { cgspLinkTableEntry 30 }

cgspLinkQ752T2E7 OBJECT-TYPE
    SYNTAX          Counter32
    UNITS           "seconds"
    MAX-ACCESS      read-only
    STATUS          current
    DESCRIPTION
        "Duration of Signalling Link unavailable due to link
        failure Q752/2.7."
    ::= { cgspLinkTableEntry 31 }

cgspLinkQ752T2E9 OBJECT-TYPE
    SYNTAX          Counter32
    UNITS           "seconds"
    MAX-ACCESS      read-only
    STATUS          current
    DESCRIPTION
        "Duration of Signalling Link unavailable due to remote
        processor outage Q752/2.9."
    REFERENCE       "ANSI GR-82-CORE 6.4.4 Link Measurements Item 31."
    ::= { cgspLinkTableEntry 32 }

cgspLinkQ752T2E10 OBJECT-TYPE
    SYNTAX          Counter32
    UNITS           "occurrences"
    MAX-ACCESS      read-only
    STATUS          current
    DESCRIPTION
        "Count of 'remote processor outage' events Q752/2.10 and
        Q752/2.11.  The standard only requires that events are
        issued.  The entries have been combined into a single
        entry to track all occurrences of these event types."
    ::= { cgspLinkTableEntry 33 }

cgspLinkQ752T2E15 OBJECT-TYPE
    SYNTAX          Counter32
    UNITS           "occurrences"
    MAX-ACCESS      read-only
    STATUS          current
    DESCRIPTION
        "Count of Status Indicator Busy received Q752/2.15."
    ::= { cgspLinkTableEntry 34 }

cgspLinkQ752T2E16 OBJECT-TYPE
    SYNTAX          Counter32
    UNITS           "occurrences"
    MAX-ACCESS      read-only
    STATUS          current
    DESCRIPTION
        "Count of local inhibition Q752/2.16 and Q752/2.17.
        The standard only requires that events are issued.
        The entries have been combined into a single
        entry to track all occurrences of these event types."
    REFERENCE       "ANSI GR-82-CORE 6.4.4 Link Measurements Item 27."
    ::= { cgspLinkTableEntry 35 }

cgspLinkQ752T2E18 OBJECT-TYPE
    SYNTAX          Counter32
    UNITS           "occurrences"
    MAX-ACCESS      read-only
    STATUS          current
    DESCRIPTION
        "Count of remote inhibition Q752/2.18 and Q752/2.19.
        The standard only requires that events are issued.
        The entries have been combined into a single
        entry to track all occurrences of these event types."
    REFERENCE       "ANSI GR-82-CORE 6.4.4 Link Measurements Item 28."
    ::= { cgspLinkTableEntry 36 }

cgspLinkQ752T3E1 OBJECT-TYPE
    SYNTAX          Counter32
    UNITS           "bytes"
    MAX-ACCESS      read-only
    STATUS          current
    DESCRIPTION
        "The number of MTP3 bytes sent by this link.
        This measurement is specified in Q752/3.1"
    REFERENCE       "ANSI GR-82-CORE 6.4.4 Link Measurements Item 4."
    ::= { cgspLinkTableEntry 37 }

cgspLinkQ752T3E2Bytes OBJECT-TYPE
    SYNTAX          Counter32
    UNITS           "bytes"
    MAX-ACCESS      read-only
    STATUS          current
    DESCRIPTION
        "The number of MTP3 bytes retransmitted on this link.
        This measurement is specified in Q752/3.2"
    ::= { cgspLinkTableEntry 38 }

cgspLinkQ752T3E2Packets OBJECT-TYPE
    SYNTAX          Counter32
    UNITS           "packets"
    MAX-ACCESS      read-only
    STATUS          current
    DESCRIPTION
        "The number of MTP3 packets retransmitted on this link.
        This measurement is specified in Q752/3.2"
    REFERENCE       "ANSI GR-82-CORE 6.4.4 Link Measurements Item 3."
    ::= { cgspLinkTableEntry 39 }

cgspLinkQ752T3E3 OBJECT-TYPE
    SYNTAX          Counter32
    UNITS           "packets"
    MAX-ACCESS      read-only
    STATUS          current
    DESCRIPTION
        "The number of MTP3 packets sent by this link.
        This measurement is specified in Q752/3.3."
    REFERENCE       "ANSI GR-82-CORE 6.4.4 Link Measurements Item 1."
    ::= { cgspLinkTableEntry 40 }

cgspLinkQ752T3E4 OBJECT-TYPE
    SYNTAX          Counter32
    UNITS           "bytes"
    MAX-ACCESS      read-only
    STATUS          current
    DESCRIPTION
        "The number of MTP3 bytes received by this link.
        This measurement is specified in Q752/3.4"
    REFERENCE       "ANSI GR-82-CORE 6.4.4 Link Measurements Item 5."
    ::= { cgspLinkTableEntry 41 }

cgspLinkQ752T3E5 OBJECT-TYPE
    SYNTAX          Counter32
    UNITS           "packets"
    MAX-ACCESS      read-only
    STATUS          current
    DESCRIPTION
        "The number of MTP3 packets received by this link.
        This measurement is specified in Q752/3.5"
    REFERENCE       "ANSI GR-82-CORE 6.4.4 Link Measurements Item 1."
    ::= { cgspLinkTableEntry 42 }

cgspLinkQ752T3E6 OBJECT-TYPE
    SYNTAX          Counter32
    UNITS           "events"
    MAX-ACCESS      read-only
    STATUS          current
    DESCRIPTION
        "The number times this Signalling link was marked
        congested. This measurement is specified in Q752/3.6"
    ::= { cgspLinkTableEntry 43 }

cgspLinkQ752T3E7 OBJECT-TYPE
    SYNTAX          Counter32
    UNITS           "seconds"
    MAX-ACCESS      read-only
    STATUS          current
    DESCRIPTION
        "Cumulative duration of Signalling link congestion
        Q752/3.7."
    REFERENCE       "ANSI GR-82-CORE 6.4.4 Link Measurements Item 11."
    ::= { cgspLinkTableEntry 44 }

cgspLinkQ752T3E10L1 OBJECT-TYPE
    SYNTAX          Counter32
    UNITS           "Packets"
    MAX-ACCESS      read-only
    STATUS          current
    DESCRIPTION
        "The number of packets(MSUs) discarded due to Signalling
        link level 1 congestion Q752/3.10"
    REFERENCE
        "ANSI GR-82-CORE 6.4.4 Link Measurements Item 17-19."
    ::= { cgspLinkTableEntry 45 }

cgspLinkQ752T3E10L2 OBJECT-TYPE
    SYNTAX          Counter32
    UNITS           "Packets"
    MAX-ACCESS      read-only
    STATUS          current
    DESCRIPTION
        "The number of packets(MSUs) discard due to Signalling
        link level 2 congestion Q752/3.10"
    REFERENCE
        "ANSI GR-82-CORE 6.4.4 Link Measurements Item 18-19."
    ::= { cgspLinkTableEntry 46 }

cgspLinkQ752T3E10L3 OBJECT-TYPE
    SYNTAX          Counter32
    UNITS           "Packets"
    MAX-ACCESS      read-only
    STATUS          current
    DESCRIPTION
        "The number of packets(MSUs) discard due to Signalling
        link level 3 congestion Q752/3.10"
    REFERENCE       "ANSI GR-82-CORE 6.4.4 Link Measurements Item 19."
    ::= { cgspLinkTableEntry 47 }

cgspLinkQ752T3E11L1 OBJECT-TYPE
    SYNTAX          Counter32
    UNITS           "occurrences"
    MAX-ACCESS      read-only
    STATUS          current
    DESCRIPTION
        "The number times this Signalling link entered congestion
        level 1 and packets were discarded. This measurement is
        specified in Q752/3.11"
    REFERENCE       "ANSI GR-82-CORE 6.4.4 Link Measurements Item 14."
    ::= { cgspLinkTableEntry 48 }

cgspLinkQ752T3E11L2 OBJECT-TYPE
    SYNTAX          Counter32
    UNITS           "occurrences"
    MAX-ACCESS      read-only
    STATUS          current
    DESCRIPTION
        "The number times this Signalling link entered congestion
        level 2 and packets were discarded. This measurement is
        specified in Q752/3.11"
    REFERENCE       "ANSI GR-82-CORE 6.4.4 Link Measurements Item 15."
    ::= { cgspLinkTableEntry 49 }

cgspLinkQ752T3E11L3 OBJECT-TYPE
    SYNTAX          Counter32
    UNITS           "occurrences"
    MAX-ACCESS      read-only
    STATUS          current
    DESCRIPTION
        "The number times this Signalling link entered congestion
        level 3 and packets were discarded. This measurement is
        specified in Q752/3.11"
    REFERENCE       "ANSI GR-82-CORE 6.4.4 Link Measurements Item 16."
    ::= { cgspLinkTableEntry 50 }

cgspLinkLocalPeerPort OBJECT-TYPE
    SYNTAX          InetPortNumber
    MAX-ACCESS      read-create
    STATUS          current
    DESCRIPTION
        "When cgspLinkType is set to 'sctpIp' then this object
        contains the local port number used to create the
        association supporting this link. This object can
        be used to obtain information from the cgsp2LocalPeerTable
        and cgsp2LpIpAddrTable Tables in the CISCO-ITP-GSP2-MIB.my
        MIB."
    ::= { cgspLinkTableEntry 51 }

cgspLinkRemotePeerPort OBJECT-TYPE
    SYNTAX          InetPortNumber
    MAX-ACCESS      read-create
    STATUS          current
    DESCRIPTION
        "When cgspLinkType is set to 'sctpIp' then this object
        contains the remote port number used to create the
        association supporting this link.
        When cgspLinkType is not set to 'sctpIp' then no
        significance is to be placed on this value."
    ::= { cgspLinkTableEntry 52 }

cgspLinkQosClass OBJECT-TYPE
    SYNTAX          CItpTcQos
    MAX-ACCESS      read-create
    STATUS          current
    DESCRIPTION
        "When cgspLinkType is set to 'sctpIp' then this object
        contains the quality of service class to be assigned
        to packets sent on this association.
        When cgspLinkType is not set to 'sctpIp' then no
        significance is to be placed on this value."
    ::= { cgspLinkTableEntry 53 }

cgspLinkDisplayName OBJECT-TYPE
    SYNTAX          SnmpAdminString (SIZE  (0..30))
    MAX-ACCESS      read-create
    STATUS          current
    DESCRIPTION
        "A short identifier for each link linkset.
        This value can be set by system administrator
        or defaults to the linkset name and SLC
        formatted as an ASCII string."
    ::= { cgspLinkTableEntry 54 }

cgspLinkDroppedPkts OBJECT-TYPE
    SYNTAX          Counter32
    UNITS           "packets"
    MAX-ACCESS      read-only
    STATUS          current
    DESCRIPTION
        "The number of packets that were dropped by this link."
    ::= { cgspLinkTableEntry 55 }

cgspLinkTransmittedLSSUs OBJECT-TYPE
    SYNTAX          Counter32
    UNITS           "LSSU"
    MAX-ACCESS      read-only
    STATUS          current
    DESCRIPTION
        "The number of Link Status Signal Units sent on this
        link."
    ::= { cgspLinkTableEntry 56 }

cgspLinkReceivedLSSUs OBJECT-TYPE
    SYNTAX          Counter32
    UNITS           "LSSU"
    MAX-ACCESS      read-only
    STATUS          current
    DESCRIPTION
        "The number of Link Status Signal Units received on this
        link."
    ::= { cgspLinkTableEntry 57 }

cgspLinkProtocolDetails OBJECT-TYPE
    SYNTAX          BITS {
                        tcbcBuffering(0),
                        tcocBuffering(1),
                        tlacAdjacentSpRestarting(2),
                        tlacEmergencyCoInProgress(3),
                        tlacChangebackInProgress(4),
                        tlacChangeoverInProgress(5),
                        tlacChangeoverFailed(6),
                        tlacInhibitRetry(7),
                        tlacManagementRequest(8),
                        tlacSpRestarting(9),
                        tsrcChangeOverComplete(10),
                        tsrcAdjacentSpRestart(11),
                        tlacLocalInhibit(12),
                        tlacRemoteInhibit(13),
                        tlacLocalBlocked(14),
                        tlacRemoteBlocked(15)
                    }
    MAX-ACCESS      read-only
    STATUS          current
    DESCRIPTION
        "This object provide details on the protocol states
        for this link as follows.

        Changeback control(TCBC)
              'tcbcBuffering': Changeback control is buffering data
                               on this link.

        Changeover control(TCOC)
              'tcocBuffering': Changeover control is buffering data
                               on this link

        Link availability control(TLAC)
              'tlacAdjacentSpRestarting': Adjacent Signalling point
                               is restarting.

              'tlacEmergencyCoInProgress': Emergency changeover is in
                               progress on this link.

              'tlacChangebackInProgress': Changeback is in progress
                               on this link.

              'tlacChangeoverInProgress': Changeover is in progress
                               on this link.

              'tlacChangeoverFailed': The last changeover operation
                               failed on this link.

              'tlacInhibitRetry': Inhibit command will be retried.

              'tlacManagementRequest': Management request in progress
                               for this link.

              'tlacSpRestarting': Signalling point is in the process
                               of a restart.

              'tlacLocalInhibit': Link has been inhibited by a
                               local management operation.

              'tlacRemoteInhibit': Link has been inhibited by a
                              remote management operation.

              'tlacLocalBlocked': Link is blocked because of a
                              local processor outage.

              'tlacRemoteBlocked': Link is blocked because of a
                              remote processor outage.

        Signalling routing control(TSRC)
              'tsrcChangeOverComplete': Changeove request is complete.

              'tsrcAdjacentSpRestart': Adjacent Signalling Point is
                               restarting."
    ::= { cgspLinkTableEntry 58 }

cgspLinkLsacState OBJECT-TYPE
    SYNTAX          INTEGER  {
                        undefined(1),
                        inactive(2),
                        active(3),
                        activatingRestoring(4),
                        failed(5),
                        actT17wait(6),
                        actAnsiWaitDeloaded(7),
                        actItuWaitStmReady(8)
                    }
    MAX-ACCESS      read-only
    STATUS          current
    DESCRIPTION
        "Signalling link activity control state:
        'undefined'  - link is an undefined state
        'inactive'   - A Signalling link that is not in
                       operation.
        'active'     - A Signalling link that is in
                       operation.
        'activatingRestoring' - A Signalling that is not operational
                       and is being activated or restored.
        'failed' - A Signalling link which is available
                       (not blocked) is marked by level 3 as
                       failed when a changeover order is
                       received.
        'actT17wait' - Link activation has failed.  Link is
                       placed into this state to wait for timer
                       T17 to expire in order to avoid the
                       oscillation of initial alignment failure
                       and link restart.
        'actAnsiWaitDeloaded - Waiting for change back
                       acknowledgement (second attempt).
        'actItuWaitStmReady' Wait for Signalling Traffic
                       Management ready event."
    REFERENCE
        "Figure 37/Q.704 - Signalling link management.
            Signalling link activity control (LSAC)"
    ::= { cgspLinkTableEntry 59 }

cgspLinkTsrcState OBJECT-TYPE
    SYNTAX          INTEGER  {
                        undefined(1),
                        idle(2),
                        wait5(3)
                    }
    MAX-ACCESS      read-only
    STATUS          current
    DESCRIPTION
        "Signalling traffic management routing control state:
        'undefined' - link is an undefined state
        'idle'      - traffic management is idle
        'wait5'     - traffic management is active and
                      in the sending status phase"
    REFERENCE
        "Figure 29/Q.704 - Signalling traffic management;
            Signalling routing control (TSRC)"
    ::= { cgspLinkTableEntry 60 }

cgspLinkTcocState OBJECT-TYPE
    SYNTAX          INTEGER  {
                        undefined(1),
                        idle(2),
                        wait2(3),
                        waitForAck(4),
                        retrieving(5),
                        wait5(6),
                        wait7(7),
                        wait8(8)
                    }
    MAX-ACCESS      read-only
    STATUS          current
    DESCRIPTION
        "Changeover control State:
        'undefined'  - Link is an undefined state.
        'idle'       - Link is available and idle.
        'wait2'      - Wait for MTP2 to initialize link.
        'waitForAck' - Waiting for changeover
                       acknowledgement.
        'retrieving' - Packets are being retrieved from
                       link.
        'wait5'      - Wait state when transitioning from
                       idle state.
        'wait7'      - Delay to avoid message mis-sequencing
                       on changeover
        'wait8'      - Wait state prior to processing
                       changeover order or emergency
                       changeover order events."
    REFERENCE
        "Figure 30/Q.704 - Signalling traffic management;
             changeover control (TCOC)"
    ::= { cgspLinkTableEntry 61 }

cgspLinkTcocLocalBSNT OBJECT-TYPE
    SYNTAX          CgspSequenceNumber
    MAX-ACCESS      read-only
    STATUS          current
    DESCRIPTION
        "The local backward sequence number to be transmitted."
    ::= { cgspLinkTableEntry 62 }

cgspLinkTcocRemoteBSNT OBJECT-TYPE
    SYNTAX          CgspSequenceNumber
    MAX-ACCESS      read-only
    STATUS          current
    DESCRIPTION
        "The remote backward sequence number to be transmitted."
    ::= { cgspLinkTableEntry 63 }

cgspLinkTcbcState OBJECT-TYPE
    SYNTAX          INTEGER  {
                        undefined(1),
                        idle(2),
                        firstAttempt(3),
                        secondAttempt(4),
                        timeControlledDiversion(5)
                    }
    MAX-ACCESS      read-only
    STATUS          current
    DESCRIPTION
        "Changeback control State:
        'undefined'     - link is an undefined state.
        'idle'          - Link is available and idle.
        'firstAttempt'  - First attempt at changeback.
        'secondAttempt' - Second attempt at changeback
        'timeControlledDiversion' - Changeback using
                           time controlled Diversion."
    ::= { cgspLinkTableEntry 64 }

cgspLinkReceivedSIBs OBJECT-TYPE
    SYNTAX          Counter32
    MAX-ACCESS      read-only
    STATUS          current
    DESCRIPTION
        "The number of status indicator 'busy' link status signal
        units received on this link. The SIB indicates that
        level two is congested at the transmitting Signalling
        point."
    ::= { cgspLinkTableEntry 65 }

cgspLinkTransmittedSIBs OBJECT-TYPE
    SYNTAX          Counter32
    MAX-ACCESS      read-only
    STATUS          current
    DESCRIPTION
        "The number of status indicator 'busy' link status signal
        units transmitted on this link. The SIB indicates that
        level two is congested at the transmitting Signalling
        point."
    ::= { cgspLinkTableEntry 66 }

cgspLinkMtp2T01Counts OBJECT-TYPE
    SYNTAX          Counter32
    MAX-ACCESS      read-only
    STATUS          current
    DESCRIPTION
        "The number of times the alignment ready timer has
        expired on this link."
    ::= { cgspLinkTableEntry 67 }

cgspLinkMtp2T02Counts OBJECT-TYPE
    SYNTAX          Counter32
    MAX-ACCESS      read-only
    STATUS          current
    DESCRIPTION
        "The number of times the not alignment ready timer has
        expired on this link."
    ::= { cgspLinkTableEntry 68 }

cgspLinkMtp2T03Counts OBJECT-TYPE
    SYNTAX          Counter32
    MAX-ACCESS      read-only
    STATUS          current
    DESCRIPTION
        "The number of times the aligned timer has
        expired on this link."
    ::= { cgspLinkTableEntry 69 }

cgspLinkMtp2T04Counts OBJECT-TYPE
    SYNTAX          Counter32
    MAX-ACCESS      read-only
    STATUS          current
    DESCRIPTION
        "The number of times the proving period timer
        has expired on this link."
    ::= { cgspLinkTableEntry 70 }

cgspLinkMtp2T05Counts OBJECT-TYPE
    SYNTAX          Counter32
    MAX-ACCESS      read-only
    STATUS          current
    DESCRIPTION
        "The number of times the sending status indicator
        busy timer has expired on this link."
    ::= { cgspLinkTableEntry 71 }

cgspLinkMtp2T06Counts OBJECT-TYPE
    SYNTAX          Counter32
    MAX-ACCESS      read-only
    STATUS          current
    DESCRIPTION
        "The number of times the remote congestion
        timer has expired on this link(Q752/1.6)."
    ::= { cgspLinkTableEntry 72 }

cgspLinkMtp2T07Counts OBJECT-TYPE
    SYNTAX          Counter32
    MAX-ACCESS      read-only
    STATUS          current
    DESCRIPTION
        "The number of times the excessive delay of
        acknowledgement timer has expired on
        this link(Q752/1.4)."
    ::= { cgspLinkTableEntry 73 }

cgspLinkOMAERMCounts OBJECT-TYPE
    SYNTAX          Counter32
    MAX-ACCESS      read-only
    STATUS          current
    DESCRIPTION
        "The number of times the Alignment Error Rate Monitor
        procedure was started on this link."
    ::= { cgspLinkTableEntry 74 }

cgspLinkOMAERMFailCounts OBJECT-TYPE
    SYNTAX          Counter32
    MAX-ACCESS      read-only
    STATUS          current
    DESCRIPTION
        "The number of times the Alignment Error Rate Monitor
        procedure failed on this link."
    ::= { cgspLinkTableEntry 75 }

cgspLinkOMSURMCounts OBJECT-TYPE
    SYNTAX          Counter32
    MAX-ACCESS      read-only
    STATUS          current
    DESCRIPTION
        "The number of times the Signal Unit Error Rate Monitor
        procedure was started on this link."
    ::= { cgspLinkTableEntry 76 }

cgspLinkOMSURMFailCounts OBJECT-TYPE
    SYNTAX          Counter32
    MAX-ACCESS      read-only
    STATUS          current
    DESCRIPTION
        "The number of times the Signal Unit Error Rate Monitor
        procedure failed on this link."
    ::= { cgspLinkTableEntry 77 }

cgspLinkPlanCapacityRcvd OBJECT-TYPE
    SYNTAX          CgspLinkCapacity
    UNITS           "bits per second"
    MAX-ACCESS      read-create
    STATUS          current
    DESCRIPTION
        "An estimate of the number of bits per second that is
        expected to be received from this link.  This
        object will be used in combination with
        cgspUtilSampleInterval, cgspUtilThreshold,
        cgspUtilThreshold and cgspLinkUtilThresholdRcvd
        to generate the ciscoGspLinkRcvdUtilChange notification."
    ::= { cgspLinkTableEntry 78 }

cgspLinkUtilThresholdRcvd OBJECT-TYPE
    SYNTAX          CgspPercentThreshold
    UNITS           "percent"
    MAX-ACCESS      read-create
    STATUS          current
    DESCRIPTION
        "This object specifies the threshold used to
        to generate the ciscoGspLinkRcvdUtilChange notification.
        The value of zero indicates the threshold has not been
        defined at the link level and the value from the
        cgspLinksetUtilThresholdRcvd or cgspUtilThreshold
        objects will be used to generate the
        ciscoGspLinkRcvdUtilChange notification."
    DEFVAL          { 0 }
    ::= { cgspLinkTableEntry 79 }

cgspLinkUtilizationRcvd OBJECT-TYPE
    SYNTAX          CgspLinkUtilization
    UNITS           "percent"
    MAX-ACCESS      read-only
    STATUS          current
    DESCRIPTION
        "An estimate of the utilization of this link for traffic
        received on this link in the prior time period defined
        by the cgspUtilSampleInterval object."
    ::= { cgspLinkTableEntry 80 }

cgspLinkUtilStateRcvd OBJECT-TYPE
    SYNTAX          CgspLinkUtilizationState
    MAX-ACCESS      read-only
    STATUS          current
    DESCRIPTION
        "Link Utilization State for inbound traffic."
    ::= { cgspLinkTableEntry 81 }

cgspLinkL2BytesRcvd OBJECT-TYPE
    SYNTAX          Counter32
    MAX-ACCESS      read-only
    STATUS          current
    DESCRIPTION
        "A count of the bytes received on the link including the
        additional bytes required by underlying protocols.
        This provides a transport independent mechanism
        for collection information on link utilization."
    ::= { cgspLinkTableEntry 82 }

cgspLinkPlanCapacitySent OBJECT-TYPE
    SYNTAX          CgspLinkCapacity
    UNITS           "bits per second"
    MAX-ACCESS      read-create
    STATUS          current
    DESCRIPTION
        "An estimate of the number of bits per second that is
        expected to be sent on this link.  This object will
        be used in combination with  cgspUtilSampleInterval,
        cgspUtilThreshold and cgspLinkUtilThresholdRcvd to
        generate the ciscoGspLinkSentUtilChange notification."
    ::= { cgspLinkTableEntry 83 }

cgspLinkUtilThresholdSent OBJECT-TYPE
    SYNTAX          CgspPercentThreshold
    UNITS           "percent"
    MAX-ACCESS      read-create
    STATUS          current
    DESCRIPTION
        "This object specifies the threshold used to generate the
        ciscoGspLinkRcvdUtilChange notification.  The value of zero
        indicates the threshold has not been defined at the link
        level and the value from the cgspLinksetUtilThresholdRcvd
        or cgspUtilThreshold objects will be used to generate the
        ciscoGspLinkRcvdUtilChange notification."
    DEFVAL          { 0 }
    ::= { cgspLinkTableEntry 84 }

cgspLinkUtilizationSent OBJECT-TYPE
    SYNTAX          CgspLinkUtilization
    UNITS           "percent"
    MAX-ACCESS      read-only
    STATUS          current
    DESCRIPTION
        "An estimate of the utilization of this link for traffic
        sent on this link in the prior time period defined
        by the cgspUtilSampleInterval object."
    ::= { cgspLinkTableEntry 85 }

cgspLinkUtilStateSent OBJECT-TYPE
    SYNTAX          CgspLinkUtilizationState
    MAX-ACCESS      read-only
    STATUS          current
    DESCRIPTION
        "Link Utilization State for out bound traffic."
    ::= { cgspLinkTableEntry 86 }

cgspLinkL2BytesSent OBJECT-TYPE
    SYNTAX          Counter32
    MAX-ACCESS      read-only
    STATUS          current
    DESCRIPTION
        "A count of the bytes sent on the link including the
        additional bytes required by underlying protocols.
        This provides a transport independent mechanism
        for collection information on link utilization."
    ::= { cgspLinkTableEntry 87 }

cgspLinkTestResult OBJECT-TYPE
    SYNTAX          CgspLinkTestResults
    MAX-ACCESS      read-only
    STATUS          current
    DESCRIPTION
        "This object provides information on result from
        signalling link test received on this link."
    ::= { cgspLinkTableEntry 88 }

cgspLinkRowStatus OBJECT-TYPE
    SYNTAX          RowStatus
    MAX-ACCESS      read-create
    STATUS          current
    DESCRIPTION
        "The object is used by a management station to
        create or delete the row entry in cgspLinkTable
        following the RowStatus textual convention."
    ::= { cgspLinkTableEntry 89 }

cgspLinkSctpAssociationId OBJECT-TYPE
    SYNTAX          Unsigned32
    MAX-ACCESS      read-only
    STATUS          current
    DESCRIPTION
        "If the link type specified by cgspLinkType is 'sctpIp',
        this is the association identifier defined in the
        Stream Control Transmission Protocol(SCTP) MIB.  Where
        value greater than zero indicates a valid association.
        The zero value indicates an association does not exist
        for this link.  This value will always be set to
        zero one when cgspLinkType is not equal to the
        'sctpIp' value. This object replaces
        cgspLinkSctpAssociation and allows association
        identifiers to be larger than 65,535."
    ::= { cgspLinkTableEntry 90 }

cgspLinkQ752T1E12 OBJECT-TYPE
    SYNTAX          Counter32
    UNITS           "occurrences"
    MAX-ACCESS      read-only
    STATUS          current
    DESCRIPTION
        "Count of 'Signalling Link Restoration' events Q752/1.12."
    ::= { cgspLinkTableEntry 91 }

cgspLinkQ752T1E12Errors OBJECT-TYPE
    SYNTAX          Counter32
    UNITS           "occurrences"
    MAX-ACCESS      read-only
    STATUS          current
    DESCRIPTION
        "Count of 'Signalling Link Restoration' error events related
        to Q752/1.12. i.e., the number of times the link restoration
        was attempted and the link was not recovered."
    ::= { cgspLinkTableEntry 92 }

cgspLinkQ752T2E11 OBJECT-TYPE
    SYNTAX          Counter32
    UNITS           "occurrences"
    MAX-ACCESS      read-only
    STATUS          current
    DESCRIPTION
        "Count of 'remote processor recovery' events Q752/2.11.
        The standard only requires that events are issued."
    ::= { cgspLinkTableEntry 93 }

cgspLinkQ752T2E17 OBJECT-TYPE
    SYNTAX          Counter32
    UNITS           "occurrences"
    MAX-ACCESS      read-only
    STATUS          current
    DESCRIPTION
        "Count of local uninhibition Q752/2.17. The standard only
        requires that events are issued."
    ::= { cgspLinkTableEntry 94 }

cgspLinkQ752T2E19 OBJECT-TYPE
    SYNTAX          Counter32
    UNITS           "occurrences"
    MAX-ACCESS      read-only
    STATUS          current
    DESCRIPTION
        "Count of remote uninhibition Q752/2.19. The standard only
        requires that events are issued."
    ::= { cgspLinkTableEntry 95 }

cgspLinkRxCongestionState OBJECT-TYPE
    SYNTAX          Unsigned32 (0..1)
    MAX-ACCESS      read-only
    STATUS          current
    DESCRIPTION
        "The Signalling link Received Side congestion status of this
        link.
        0 abate, 1 onset is the received side congestion level"
    ::= { cgspLinkTableEntry 96 }


-- *************************************************************
-- *                                                           *
-- * Link Timer Table                                          *
-- *                                                           *
-- *************************************************************

cgspLinkTimerTable OBJECT-TYPE
    SYNTAX          SEQUENCE OF CgspLinkTimerTableEntry
    MAX-ACCESS      not-accessible
    STATUS          current
    DESCRIPTION
        "A table that contains the timer used to configure timer
        values specific to a particular Link.  Entries are added
        to this table via cgspLinkTimerRowStatus in accordance
        with the RowStatus convention."
    ::= { cgspLink 2 }

cgspLinkTimerTableEntry OBJECT-TYPE
    SYNTAX          CgspLinkTimerTableEntry
    MAX-ACCESS      not-accessible
    STATUS          current
    DESCRIPTION
        "This table is used to configure all MTP3 timer
        values that apply to links.  The values apply
        to a particular link."
    INDEX           {
                        cgspInstNetwork,
                        cgspLinksetName,
                        cgspLinkSlc,
                        cgspLinkTimerNumber
                    }
    ::= { cgspLinkTimerTable 1 }

CgspLinkTimerTableEntry ::= SEQUENCE {
        cgspLinkTimerNumber    CgspTimerNumbers,
        cgspLinkTimerValue     CgspTimerValue,
        cgspLinkTimerRowStatus RowStatus
}

cgspLinkTimerNumber OBJECT-TYPE
    SYNTAX          CgspTimerNumbers
    MAX-ACCESS      not-accessible
    STATUS          current
    DESCRIPTION
        "Index into table containing timer information."
    ::= { cgspLinkTimerTableEntry 1 }

cgspLinkTimerValue OBJECT-TYPE
    SYNTAX          CgspTimerValue
    UNITS           "milliseconds"
    MAX-ACCESS      read-create
    STATUS          current
    DESCRIPTION
        "Value of timer selected by cgspLinkTimerNumber object."
    ::= { cgspLinkTimerTableEntry 2 }

cgspLinkTimerRowStatus OBJECT-TYPE
    SYNTAX          RowStatus
    MAX-ACCESS      read-create
    STATUS          current
    DESCRIPTION
        "The object is used by a management station to
        create or delete the row entry in cgspLinkTimerTable
        following the RowStatus textual convention."
    ::= { cgspLinkTimerTableEntry 3 }


-- *************************************************************
-- *                                                           *
-- * Link Remote Ip Address Table                              *
-- *                                                           *
-- *************************************************************

cgspLinkRemoteIpAddrTable OBJECT-TYPE
    SYNTAX          SEQUENCE OF CgspLinkRemoteIpAddrTableEntry
    MAX-ACCESS      not-accessible
    STATUS          current
    DESCRIPTION
        "A table that contains the remote IP addresses used to
        configure a particular Link.  Entries are added
        to this table via cgspLinkRemoteIpAddrRowStatus in
        accordance with the RowStatus convention."
    ::= { cgspLink 3 }

cgspLinkRemoteIpAddrTableEntry OBJECT-TYPE
    SYNTAX          CgspLinkRemoteIpAddrTableEntry
    MAX-ACCESS      not-accessible
    STATUS          current
    DESCRIPTION
        "A list of remote IP addresses per Link."
    INDEX           {
                        cgspInstNetwork,
                        cgspLinksetName,
                        cgspLinkSlc,
                        cgspLinkRemoteIpAddrNumber
                    }
    ::= { cgspLinkRemoteIpAddrTable 1 }

CgspLinkRemoteIpAddrTableEntry ::= SEQUENCE {
        cgspLinkRemoteIpAddrNumber    Unsigned32,
        cgspLinkRemoteIpAddrType      InetAddressType,
        cgspLinkRemoteIpAddress       InetAddress,
        cgspLinkRemoteIpAddrRowStatus RowStatus
}

cgspLinkRemoteIpAddrNumber OBJECT-TYPE
    SYNTAX          Unsigned32 (1..65535)
    MAX-ACCESS      not-accessible
    STATUS          current
    DESCRIPTION
        "This object specifies the index for the IP
        addresses in the remote IP Address table"
    ::= { cgspLinkRemoteIpAddrTableEntry 1 }

cgspLinkRemoteIpAddrType OBJECT-TYPE
    SYNTAX          InetAddressType
    MAX-ACCESS      read-create
    STATUS          current
    DESCRIPTION
        "This object contains the type of the local
        IP address used to create an association."
    ::= { cgspLinkRemoteIpAddrTableEntry 2 }

cgspLinkRemoteIpAddress OBJECT-TYPE
    SYNTAX          InetAddress
    MAX-ACCESS      read-create
    STATUS          current
    DESCRIPTION
        "This object contains the remote IP address used to
        create the association with the partner of this
         association."
    ::= { cgspLinkRemoteIpAddrTableEntry 3 }

cgspLinkRemoteIpAddrRowStatus OBJECT-TYPE
    SYNTAX          RowStatus
    MAX-ACCESS      read-create
    STATUS          current
    DESCRIPTION
        "The object is used by a management station to create
        or delete the row entry in cgspLinkRemoteIpAddrTable
        following the RowStatus textual convention."
    ::= { cgspLinkRemoteIpAddrTableEntry 4 }


-- *************************************************************
-- *                                                           *
-- * Link Utilization table                                    *
-- *                                                           *
-- *************************************************************

cgspLinkUtilTable OBJECT-TYPE
    SYNTAX          SEQUENCE OF CgspLinkUtilTableEntry
    MAX-ACCESS      not-accessible
    STATUS          current
    DESCRIPTION
        "A table that contains a history of the
        cgspLinkUtilizationRcvd and cgspLinkUtilizationRcvd
        objects.  In order to properly manage network capacity
        it is necessary to collect utilization information during
        short interval.  These intervals are less than 5 minutes and
        can be as low as 1 minute.  The number of links supported by
        a signalling point prevent polling each signalling point
        to collect information.  This table is provided to allow an
        NMS to collect the information during a normal poll cycle."
    ::= { cgspLink 4 }

cgspLinkUtilTableEntry OBJECT-TYPE
    SYNTAX          CgspLinkUtilTableEntry
    MAX-ACCESS      not-accessible
    STATUS          current
    DESCRIPTION
        "A collection of entries used to store a history
        link utilization values.  Values from
        cgspLinkUtilizationRcvd and cgspLinkUtilizationSent
        objects are saved in cgspLinkUtilRcvd and
        cgspLinkUtilSent."
    INDEX           {
                        cgspInstNetwork,
                        cgspLinksetName,
                        cgspLinkSlc,
                        cgspLinkUtilIndex
                    }
    ::= { cgspLinkUtilTable 1 }

CgspLinkUtilTableEntry ::= SEQUENCE {
        cgspLinkUtilIndex        Unsigned32,
        cgspLinkUtilRcvd         CgspLinkUtilization,
        cgspLinkUtilSent         CgspLinkUtilization,
        cgspLinkUtilEndTimestamp TimeStamp
}

cgspLinkUtilIndex OBJECT-TYPE
    SYNTAX          Unsigned32 (1..60)
    MAX-ACCESS      not-accessible
    STATUS          current
    DESCRIPTION
        "Index used to access historical link utilization
        information.  Entry one corresponds to the most
        recent utilization window for the length of time
        specified by the cgspUtilSampleInterval object.
        Example of utilization history using default values.

        Current Time: 10:42 am  Sample Interval: 300 seconds
        cgspLinkUtilIndex
        [1]               Window from 10:36-10:41
        [2]               Window from 10:31-10:36
        [3]               Window from 10:26-10:31
         .
         .
        [n]

        The index ranges from one to a maximum of sixty entries.
        The actual number of entries will depend on the
        implementation and available resources."
    ::= { cgspLinkUtilTableEntry 1 }

cgspLinkUtilRcvd OBJECT-TYPE
    SYNTAX          CgspLinkUtilization
    UNITS           "percent"
    MAX-ACCESS      read-only
    STATUS          current
    DESCRIPTION
        "An estimate of the utilization of this link for traffic
        received on this link in the time period defined
        by the cgspUtilSampleInterval object."
    ::= { cgspLinkUtilTableEntry 2 }

cgspLinkUtilSent OBJECT-TYPE
    SYNTAX          CgspLinkUtilization
    UNITS           "percent"
    MAX-ACCESS      read-only
    STATUS          current
    DESCRIPTION
        "An estimate of the utilization of this link for traffic
        transmitted on this link in the time period defined
        by the cgspUtilSampleInterval object."
    ::= { cgspLinkUtilTableEntry 3 }

cgspLinkUtilEndTimestamp OBJECT-TYPE
    SYNTAX          TimeStamp
    MAX-ACCESS      read-only
    STATUS          current
    DESCRIPTION
        "This timestamp indicates when time period ended
        for this sample."
    ::= { cgspLinkUtilTableEntry 4 }



-- *************************************************************
-- *                                                           *
-- * GSP - Notification Enable     Objects                     *
-- *                                                           *
-- *************************************************************

cgspLsStateChangeNotifEnabled OBJECT-TYPE
    SYNTAX          TruthValue
    MAX-ACCESS      read-write
    STATUS          current
    DESCRIPTION
        "The signalling point linkset notification truth
        value.
        'true'  Indicates that ciscoGspLinksetStateChange
               notification is to be generated when the state
               changes. That is, the notification generation
               is enabled.
        'false' Indicates that ciscoGspLinksetStateChange
               notification generation is disabled."
    DEFVAL          { false }
    ::= { cgspNotificationsEnable 1 }

cgspLnkStateChangeNotifEnabled OBJECT-TYPE
    SYNTAX          TruthValue
    MAX-ACCESS      read-write
    STATUS          current
    DESCRIPTION
        "The signalling point link notification truth value.
        'true'  Indicates that ciscoGspLinkStateChange
                notification is to be generated when the state
                changes. That is, the notification generation
                is enabled.
        'false' Indicates that ciscoGspLinkStateChange
                notification generation is disabled."
    DEFVAL          { false }
    ::= { cgspNotificationsEnable 2 }

cgspCongestionNotifEnabled OBJECT-TYPE
    SYNTAX          TruthValue
    MAX-ACCESS      read-write
    STATUS          current
    DESCRIPTION
        "The signalling point congestion notification truth
        value.
        'true'  Indicates that ciscoGspCongestionChange and
              ciscoGspRxCongestionChange notification is to be
        generated       when the state changes. That is, the
        notification       generation is enabled.
        'false' Indicates that ciscoGspCongestionChange and
              ciscoGspRxCongestionChange notification generation is
              disabled."
    DEFVAL          { false }
    ::= { cgspNotificationsEnable 3 }

cgspLinkUtilNotifEnabled OBJECT-TYPE
    SYNTAX          TruthValue
    MAX-ACCESS      read-write
    STATUS          current
    DESCRIPTION
        "The signalling point link utilization notification
        truth value.
        'true'  Indicates that the notification of link
                utilization has been enabled.  That is,
                the notification generation is enabled.

        'false' Indicates that the notification link
                utilization has been disabled."
    DEFVAL          { false }
    ::= { cgspNotificationsEnable 4 }

cgspIsolationNotifEnabled OBJECT-TYPE
    SYNTAX          TruthValue
    MAX-ACCESS      read-write
    STATUS          current
    DESCRIPTION
        "The isolation notification truth value.
        'true'  Indicates that the notification of
                isolation has been enabled.  That is,
                the notification generation is enabled.

        'false' Indicates that the notification
                of isolation has been disabled."
    DEFVAL          { false }
    ::= { cgspNotificationsEnable 5 }

cgspUPUNotifEnabled OBJECT-TYPE
    SYNTAX          TruthValue
    MAX-ACCESS      read-write
    STATUS          current
    DESCRIPTION
        "A control to enable or disable both ciscoGspUPUReceived
        and ciscoGspUPUTransmitted notifications as follows:
        'true'  Indicates that the ciscoGspUPUReceived and
              ciscoGspUPUTransmitted notification generation
              is enabled.
        'false' Indicates that ciscoGspUPUReceived and
              ciscoGspUPUTransmitted notification generation
              is disabled."
    DEFVAL          { false }
    ::= { cgspNotificationsEnable 6 }

-- *************************************************************
-- *                                                           *
-- * Notifications Information                                 *
-- *                                                           *
-- *************************************************************

cgspUPUIntervalDuration OBJECT-TYPE
    SYNTAX          Unsigned32
    UNITS           "seconds"
    MAX-ACCESS      accessible-for-notify
    STATUS          current
    DESCRIPTION
        "Duration elapsed since the start of the cgspUPUNotifWindowTime
        interval. This duration value can range from 0 upto
        cgspUPUNotifWindowTime.  For the notifications generated
        at the end of the interval, this value will be equal to
        cgspUPUNotifWindowTime."
    ::= { cgspNotificationsInfo 1 }

cgspIntervalUPUs OBJECT-TYPE
    SYNTAX          Unsigned32
    UNITS           "MSUs"
    MAX-ACCESS      accessible-for-notify
    STATUS          current
    DESCRIPTION
        "Number of UPU MSUs received or transmitted during this
        specific cgspUPUIntervalDuration interval."
    ::= { cgspNotificationsInfo 2 }

-- *************************************************************
-- *                                                           *
-- * Notifications                                             *
-- *                                                           *
-- *************************************************************

ciscoGspLinksetStateChange NOTIFICATION-TYPE
    OBJECTS         {
                        cgspEventSequenceNumber,
                        cgspCLLICode,
                        cgspLinksetDisplayName,
                        cgspLinksetSourceDisplayPC,
                        cgspLinksetAdjacentDisplayPC,
                        cgspLinksetState
                    }
    STATUS          current
    DESCRIPTION
        "The notification generated when a linkset
        changes to a new state.  The value of
        cgspLinksetState  indicates the new state."
   ::= { ciscoGspMIBNotifs 1 }

ciscoGspLinkStateChange NOTIFICATION-TYPE
    OBJECTS         {
                        cgspEventSequenceNumber,
                        cgspCLLICode,
                        cgspLinksetSourceDisplayPC,
                        cgspLinksetAdjacentDisplayPC,
                        cgspLinkDisplayName,
                        cgspLinkState,
                        cgspLinkReason,
                        cgspLinkTestResult
                    }
    STATUS          current
    DESCRIPTION
        "The notification generated when a link
        changes to a new state.  The value of
        cgspLinkState  indicates the new state."
   ::= { ciscoGspMIBNotifs 2 }

ciscoGspCongestionChange NOTIFICATION-TYPE
    OBJECTS         {
                        cgspEventSequenceNumber,
                        cgspCLLICode,
                        cgspLinksetSourceDisplayPC,
                        cgspLinksetAdjacentDisplayPC,
                        cgspLinkDisplayName,
                        cgspLinkCongestionState
                    }
    STATUS          current
    DESCRIPTION
        "The notification generated when a link
        changes to a new congestion level as specified
        by cgspLinkCongestionState object for Transmission Side
            congestion."
   ::= { ciscoGspMIBNotifs 3 }

ciscoGspLinkRcvdUtilChange NOTIFICATION-TYPE
    OBJECTS         {
                        cgspEventSequenceNumber,
                        cgspCLLICode,
                        cgspLinksetSourceDisplayPC,
                        cgspLinksetAdjacentDisplayPC,
                        cgspLinkDisplayName,
                        cgspLinkUtilStateRcvd,
                        cgspLinkUtilizationRcvd
                    }
    STATUS          current
    DESCRIPTION
        "The notification provide is generated when
        the cgspLinkUtilStateRcvd changes states."
   ::= { ciscoGspMIBNotifs 4 }

ciscoGspLinkSentUtilChange NOTIFICATION-TYPE
    OBJECTS         {
                        cgspEventSequenceNumber,
                        cgspCLLICode,
                        cgspLinksetSourceDisplayPC,
                        cgspLinksetAdjacentDisplayPC,
                        cgspLinkDisplayName,
                        cgspLinkUtilStateSent,
                        cgspLinkUtilizationSent
                    }
    STATUS          current
    DESCRIPTION
        "The notification provide is generated when
        the cgspLinkUtilStateSent changes states."
   ::= { ciscoGspMIBNotifs 5 }

ciscoGspIsolation NOTIFICATION-TYPE
    OBJECTS         {
                        cgspEventSequenceNumber,
                        cgspCLLICode,
                        cgspInstDisplayName,
                        cgspInstDescription
                    }
    STATUS          current
    DESCRIPTION
        "This notification indicates the instance specified
        by cgspInstDisplayName and cgspInstDescription has
        become isolated. All linkset used to connect MTP3 node
        (instance) are unavailable.  Isolation is ended when
        any linkset supported by this instance reaches the
        active state."
   ::= { ciscoGspMIBNotifs 6 }

ciscoGspUPUReceived NOTIFICATION-TYPE
    OBJECTS         {
                        cgspEventSequenceNumber,
                        cgspCLLICode,
                        cgspInstUserPartDisplay,
                        cgspUPUIntervalDuration,
                        cgspIntervalUPUs
                    }
    STATUS          current
    DESCRIPTION
        "The notification is generated when an UPU MSU is received
        from a remote signalling point, for a specific instance
        and user part for the first time in the configured
        cgspUPUNotifWindowTime. For cases when there is a non-zero
        number of UPU MSUs received, this notification will be sent
        at the end of the cgspUPUNotifWindowTime interval, with
        cgspIntervalUPUs indicating the total count of UPU
        MSUs received for that specific instance and user part
        during the entire cgspUPUNotifWindowTime interval Q752/5.6."
   ::= { ciscoGspMIBNotifs 8 }

ciscoGspUPUTransmitted NOTIFICATION-TYPE
    OBJECTS         {
                        cgspEventSequenceNumber,
                        cgspCLLICode,
                        cgspInstUserPartDisplay,
                        cgspUPUIntervalDuration,
                        cgspIntervalUPUs
                    }
    STATUS          current
    DESCRIPTION
        "The notification is generated when an UPU MSU is transmitted
        to a remote signalling point, for a specific instance and
        user part for the first time in the configured
        cgspUPUNotifWindowTime. For cases when there is a non-zero
        number of UPU MSUs received, this notification will be sent
        at the end of the cgspUPUNotifWindowTime interval, with
        cgspIntervalUPUs indicating the total count of UPU MSUs
        transmitted for that specific instance and user part
        during the entire cgspUPUNotifWindowTime interval Q752/5.7."
   ::= { ciscoGspMIBNotifs 9 }

ciscoGspRxCongestionChange NOTIFICATION-TYPE
    OBJECTS         {
                        cgspEventSequenceNumber,
                        cgspCLLICode,
                        cgspLinksetSourceDisplayPC,
                        cgspLinksetAdjacentDisplayPC,
                        cgspLinkDisplayName,
                        cgspLinkRxCongestionState
                    }
    STATUS          current
    DESCRIPTION
        "The notification generated when a link
        changes to a new congestion level as specified
        by cgspLinkRxCongestionstate object for Received side
        congestion"
   ::= { ciscoGspMIBNotifs 10 }
-- Conformance Information

ciscoGspMIBCompliances  OBJECT IDENTIFIER
    ::= { ciscoGspMIBConform 1 }

ciscoGspMIBGroups  OBJECT IDENTIFIER
    ::= { ciscoGspMIBConform 2 }


-- Compliance

ciscoGspMIBCompliance MODULE-COMPLIANCE
    STATUS          deprecated
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkGroup,
                        ciscoGspLinkTimerGroup,
                        ciscoGspLinkRemoteIpGroup,
                        ciscoGspLinkUtilGroup,
                        ciscoGspNotificationsEnableGroup,
                        ciscoGspNotificationsGroup
                    }

    OBJECT          cgspCLLICode
    MIN-ACCESS      read-only
    DESCRIPTION
        "Create/Write access is not required."

    OBJECT          cgspUtilSampleInterval
    MIN-ACCESS      read-only
    DESCRIPTION
        "Create/Write access is not required."

    OBJECT          cgspUtilThreshold
    MIN-ACCESS      read-only
    DESCRIPTION
        "Create/Write access is not required."

    OBJECT          cgspUtilAbateDelta
    MIN-ACCESS      read-only
    DESCRIPTION
        "Create/Write access is not required."

    OBJECT          cgspPlanCapacityDefault
    MIN-ACCESS      read-only
    DESCRIPTION
        "Create/Write access is not required."

    OBJECT          cgspProfileVariant
    MIN-ACCESS      read-only
    DESCRIPTION
        "Create/Write access is not required."

    OBJECT          cgspProfileMtp2BundleTimer
    MIN-ACCESS      read-only
    DESCRIPTION
        "Create/Write access is not required."

    OBJECT          cgspProfileMtp2SendQueueDepth
    MIN-ACCESS      read-only
    DESCRIPTION
        "Create/Write access is not required."

    OBJECT          cgspProfileRowStatus
    MIN-ACCESS      read-only
    DESCRIPTION
        "Create/Write access is not required."

    OBJECT          cgspProfileTimerValue
    MIN-ACCESS      read-only
    DESCRIPTION
        "Create/Write access is not required."

    OBJECT          cgspProfileTimerRowStatus
    MIN-ACCESS      read-only
    DESCRIPTION
        "Create/Write access is not required."

    OBJECT          cgspInstNetworkIndicator
    MIN-ACCESS      read-only
    DESCRIPTION
        "Create/Write access is not required."

    OBJECT          cgspInstVariant
    MIN-ACCESS      read-only
    DESCRIPTION
        "Create/Write access is not required."

    OBJECT          cgspInstDisplayName
    MIN-ACCESS      read-only
    DESCRIPTION
        "Create/Write access is not required."

    OBJECT          cgspInstDescription
    MIN-ACCESS      read-only
    DESCRIPTION
        "Create/Write access is not required."

    OBJECT          cgspInstTFR
    MIN-ACCESS      read-only
    DESCRIPTION
        "Create/Write access is not required."

    OBJECT          cgspInstCongestionsLevels
    MIN-ACCESS      read-only
    DESCRIPTION
        "Create/Write access is not required."

    OBJECT          cgspInstFastRestart
    MIN-ACCESS      read-only
    DESCRIPTION
        "Create/Write access is not required."

    OBJECT          cgspInstDistSccpUnseq
    MIN-ACCESS      read-only
    DESCRIPTION
        "Create/Write access is not required."

    OBJECT          cgspInstSummaryRoutingException
    MIN-ACCESS      read-only
    DESCRIPTION
        "Create/Write access is not required."

    OBJECT          cgspInstRouteTableName
    MIN-ACCESS      read-only
    DESCRIPTION
        "Create/Write access is not required."

    OBJECT          cgspInstRowStatus
    MIN-ACCESS      read-only
    DESCRIPTION
        "Create/Write access is not required."

    OBJECT          cgspInstTimerValue
    MIN-ACCESS      read-only
    DESCRIPTION
        "Create/Write access is not required."

    OBJECT          cgspInstTimerRowStatus
    MIN-ACCESS      read-only
    DESCRIPTION
        "Create/Write access is not required."

    OBJECT          cgspPointCodeType
    MIN-ACCESS      read-only
    DESCRIPTION
        "Create/Write access is not required."

    OBJECT          cgspPointCodeRowStatus
    MIN-ACCESS      read-only
    DESCRIPTION
        "Create/Write access is not required."

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinksetDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinkDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."
    ::= { ciscoGspMIBCompliances 1 }

ciscoGspMIBComplianceRev1 MODULE-COMPLIANCE
    STATUS          deprecated
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkTimerGroup,
                        ciscoGspLinkRemoteIpGroup,
                        ciscoGspLinkUtilGroup,
                        ciscoGspNotificationsEnableGroup,
                        ciscoGspNotificationsGroup,
                        ciscoGspLinkGroupRev1
                    }

    OBJECT          cgspCLLICode
    MIN-ACCESS      read-only
    DESCRIPTION
        "Create/Write access is not required."

    OBJECT          cgspUtilSampleInterval
    MIN-ACCESS      read-only
    DESCRIPTION
        "Create/Write access is not required."

    OBJECT          cgspUtilThreshold
    MIN-ACCESS      read-only
    DESCRIPTION
        "Create/Write access is not required."

    OBJECT          cgspUtilAbateDelta
    MIN-ACCESS      read-only
    DESCRIPTION
        "Create/Write access is not required."

    OBJECT          cgspPlanCapacityDefault
    MIN-ACCESS      read-only
    DESCRIPTION
        "Create/Write access is not required."

    OBJECT          cgspProfileVariant
    MIN-ACCESS      read-only
    DESCRIPTION
        "Create/Write access is not required."

    OBJECT          cgspProfileMtp2BundleTimer
    MIN-ACCESS      read-only
    DESCRIPTION
        "Create/Write access is not required."

    OBJECT          cgspProfileMtp2SendQueueDepth
    MIN-ACCESS      read-only
    DESCRIPTION
        "Create/Write access is not required."

    OBJECT          cgspProfileRowStatus
    MIN-ACCESS      read-only
    DESCRIPTION
        "Create/Write access is not required."

    OBJECT          cgspProfileTimerValue
    MIN-ACCESS      read-only
    DESCRIPTION
        "Create/Write access is not required."

    OBJECT          cgspProfileTimerRowStatus
    MIN-ACCESS      read-only
    DESCRIPTION
        "Create/Write access is not required."

    OBJECT          cgspInstNetworkIndicator
    MIN-ACCESS      read-only
    DESCRIPTION
        "Create/Write access is not required."

    OBJECT          cgspInstVariant
    MIN-ACCESS      read-only
    DESCRIPTION
        "Create/Write access is not required."

    OBJECT          cgspInstDisplayName
    MIN-ACCESS      read-only
    DESCRIPTION
        "Create/Write access is not required."

    OBJECT          cgspInstDescription
    MIN-ACCESS      read-only
    DESCRIPTION
        "Create/Write access is not required."

    OBJECT          cgspInstTFR
    MIN-ACCESS      read-only
    DESCRIPTION
        "Create/Write access is not required."

    OBJECT          cgspInstCongestionsLevels
    MIN-ACCESS      read-only
    DESCRIPTION
        "Create/Write access is not required."

    OBJECT          cgspInstFastRestart
    MIN-ACCESS      read-only
    DESCRIPTION
        "Create/Write access is not required."

    OBJECT          cgspInstDistSccpUnseq
    MIN-ACCESS      read-only
    DESCRIPTION
        "Create/Write access is not required."

    OBJECT          cgspInstSummaryRoutingException
    MIN-ACCESS      read-only
    DESCRIPTION
        "Create/Write access is not required."

    OBJECT          cgspInstRouteTableName
    MIN-ACCESS      read-only
    DESCRIPTION
        "Create/Write access is not required."

    OBJECT          cgspInstRowStatus
    MIN-ACCESS      read-only
    DESCRIPTION
        "Create/Write access is not required."

    OBJECT          cgspInstTimerValue
    MIN-ACCESS      read-only
    DESCRIPTION
        "Create/Write access is not required."

    OBJECT          cgspInstTimerRowStatus
    MIN-ACCESS      read-only
    DESCRIPTION
        "Create/Write access is not required."

    OBJECT          cgspPointCodeType
    MIN-ACCESS      read-only
    DESCRIPTION
        "Create/Write access is not required."

    OBJECT          cgspPointCodeRowStatus
    MIN-ACCESS      read-only
    DESCRIPTION
        "Create/Write access is not required."

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinksetDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinkDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."
    ::= { ciscoGspMIBCompliances 2 }

ciscoGspMIBComplianceRev2 MODULE-COMPLIANCE
    STATUS          deprecated
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkTimerGroup,
                        ciscoGspLinkRemoteIpGroup,
                        ciscoGspLinkUtilGroup,
                        ciscoGspNotificationsEnableGroup,
                        ciscoGspNotificationsGroup,
                        ciscoGspLinkGroupRev1,
                        ciscoGspNotificationsEnableGroupSup1,
                        ciscoGspNotificationsGroupSup1
                    }

    OBJECT          cgspCLLICode
    MIN-ACCESS      read-only
    DESCRIPTION
        "Create/Write access is not required."

    OBJECT          cgspUtilSampleInterval
    MIN-ACCESS      read-only
    DESCRIPTION
        "Create/Write access is not required."

    OBJECT          cgspUtilThreshold
    MIN-ACCESS      read-only
    DESCRIPTION
        "Create/Write access is not required."

    OBJECT          cgspUtilAbateDelta
    MIN-ACCESS      read-only
    DESCRIPTION
        "Create/Write access is not required."

    OBJECT          cgspPlanCapacityDefault
    MIN-ACCESS      read-only
    DESCRIPTION
        "Create/Write access is not required."

    OBJECT          cgspProfileVariant
    MIN-ACCESS      read-only
    DESCRIPTION
        "Create/Write access is not required."

    OBJECT          cgspProfileMtp2BundleTimer
    MIN-ACCESS      read-only
    DESCRIPTION
        "Create/Write access is not required."

    OBJECT          cgspProfileMtp2SendQueueDepth
    MIN-ACCESS      read-only
    DESCRIPTION
        "Create/Write access is not required."

    OBJECT          cgspProfileRowStatus
    MIN-ACCESS      read-only
    DESCRIPTION
        "Create/Write access is not required."

    OBJECT          cgspProfileTimerValue
    MIN-ACCESS      read-only
    DESCRIPTION
        "Create/Write access is not required."

    OBJECT          cgspProfileTimerRowStatus
    MIN-ACCESS      read-only
    DESCRIPTION
        "Create/Write access is not required."

    OBJECT          cgspInstNetworkIndicator
    MIN-ACCESS      read-only
    DESCRIPTION
        "Create/Write access is not required."

    OBJECT          cgspInstVariant
    MIN-ACCESS      read-only
    DESCRIPTION
        "Create/Write access is not required."

    OBJECT          cgspInstDisplayName
    MIN-ACCESS      read-only
    DESCRIPTION
        "Create/Write access is not required."

    OBJECT          cgspInstDescription
    MIN-ACCESS      read-only
    DESCRIPTION
        "Create/Write access is not required."

    OBJECT          cgspInstTFR
    MIN-ACCESS      read-only
    DESCRIPTION
        "Create/Write access is not required."

    OBJECT          cgspInstCongestionsLevels
    MIN-ACCESS      read-only
    DESCRIPTION
        "Create/Write access is not required."

    OBJECT          cgspInstFastRestart
    MIN-ACCESS      read-only
    DESCRIPTION
        "Create/Write access is not required."

    OBJECT          cgspInstDistSccpUnseq
    MIN-ACCESS      read-only
    DESCRIPTION
        "Create/Write access is not required."

    OBJECT          cgspInstSummaryRoutingException
    MIN-ACCESS      read-only
    DESCRIPTION
        "Create/Write access is not required."

    OBJECT          cgspInstRouteTableName
    MIN-ACCESS      read-only
    DESCRIPTION
        "Create/Write access is not required."

    OBJECT          cgspInstRowStatus
    MIN-ACCESS      read-only
    DESCRIPTION
        "Create/Write access is not required."

    OBJECT          cgspInstTimerValue
    MIN-ACCESS      read-only
    DESCRIPTION
        "Create/Write access is not required."

    OBJECT          cgspInstTimerRowStatus
    MIN-ACCESS      read-only
    DESCRIPTION
        "Create/Write access is not required."

    OBJECT          cgspPointCodeType
    MIN-ACCESS      read-only
    DESCRIPTION
        "Create/Write access is not required."

    OBJECT          cgspPointCodeRowStatus
    MIN-ACCESS      read-only
    DESCRIPTION
        "Create/Write access is not required."

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinksetDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinkDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."
    ::= { ciscoGspMIBCompliances 3 }

ciscoGspMIBComplianceRev3 MODULE-COMPLIANCE
    STATUS          deprecated
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkTimerGroup,
                        ciscoGspLinkRemoteIpGroup,
                        ciscoGspLinkUtilGroup,
                        ciscoGspNotificationsEnableGroup,
                        ciscoGspNotificationsGroup,
                        ciscoGspLinkGroupRev1,
                        ciscoGspNotificationsEnableGroupSup1,
                        ciscoGspNotificationsGroupSup1,
                        ciscoGspLinkGroupSup1,
                        ciscoGspScalarsGroupSup1,
                        ciscoGspInstUPUGroup,
                        ciscoGspNotificationsInfoGroup,
                        ciscoGspNotificationsEnableGroupSup2,
                        ciscoGspNotificationsGroupSup2
                    }

    OBJECT          cgspCLLICode
    MIN-ACCESS      read-only
    DESCRIPTION
        "Create/Write access is not required."

    OBJECT          cgspUtilSampleInterval
    MIN-ACCESS      read-only
    DESCRIPTION
        "Create/Write access is not required."

    OBJECT          cgspUtilThreshold
    MIN-ACCESS      read-only
    DESCRIPTION
        "Create/Write access is not required."

    OBJECT          cgspUtilAbateDelta
    MIN-ACCESS      read-only
    DESCRIPTION
        "Create/Write access is not required."

    OBJECT          cgspPlanCapacityDefault
    MIN-ACCESS      read-only
    DESCRIPTION
        "Create/Write access is not required."

    OBJECT          cgspProfileVariant
    MIN-ACCESS      read-only
    DESCRIPTION
        "Create/Write access is not required."

    OBJECT          cgspProfileMtp2BundleTimer
    MIN-ACCESS      read-only
    DESCRIPTION
        "Create/Write access is not required."

    OBJECT          cgspProfileMtp2SendQueueDepth
    MIN-ACCESS      read-only
    DESCRIPTION
        "Create/Write access is not required."

    OBJECT          cgspProfileRowStatus
    MIN-ACCESS      read-only
    DESCRIPTION
        "Create/Write access is not required."

    OBJECT          cgspProfileTimerValue
    MIN-ACCESS      read-only
    DESCRIPTION
        "Create/Write access is not required."

    OBJECT          cgspProfileTimerRowStatus
    MIN-ACCESS      read-only
    DESCRIPTION
        "Create/Write access is not required."

    OBJECT          cgspInstNetworkIndicator
    MIN-ACCESS      read-only
    DESCRIPTION
        "Create/Write access is not required."

    OBJECT          cgspInstVariant
    MIN-ACCESS      read-only
    DESCRIPTION
        "Create/Write access is not required."

    OBJECT          cgspInstDisplayName
    MIN-ACCESS      read-only
    DESCRIPTION
        "Create/Write access is not required."

    OBJECT          cgspInstDescription
    MIN-ACCESS      read-only
    DESCRIPTION
        "Create/Write access is not required."

    OBJECT          cgspInstTFR
    MIN-ACCESS      read-only
    DESCRIPTION
        "Create/Write access is not required."

    OBJECT          cgspInstCongestionsLevels
    MIN-ACCESS      read-only
    DESCRIPTION
        "Create/Write access is not required."

    OBJECT          cgspInstFastRestart
    MIN-ACCESS      read-only
    DESCRIPTION
        "Create/Write access is not required."

    OBJECT          cgspInstDistSccpUnseq
    MIN-ACCESS      read-only
    DESCRIPTION
        "Create/Write access is not required."

    OBJECT          cgspInstSummaryRoutingException
    MIN-ACCESS      read-only
    DESCRIPTION
        "Create/Write access is not required."

    OBJECT          cgspInstRouteTableName
    MIN-ACCESS      read-only
    DESCRIPTION
        "Create/Write access is not required."

    OBJECT          cgspInstRowStatus
    MIN-ACCESS      read-only
    DESCRIPTION
        "Create/Write access is not required."

    OBJECT          cgspInstTimerValue
    MIN-ACCESS      read-only
    DESCRIPTION
        "Create/Write access is not required."

    OBJECT          cgspInstTimerRowStatus
    MIN-ACCESS      read-only
    DESCRIPTION
        "Create/Write access is not required."

    OBJECT          cgspPointCodeType
    MIN-ACCESS      read-only
    DESCRIPTION
        "Create/Write access is not required."

    OBJECT          cgspPointCodeRowStatus
    MIN-ACCESS      read-only
    DESCRIPTION
        "Create/Write access is not required."

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinksetDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinkDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."
    ::= { ciscoGspMIBCompliances 4 }

ciscoGspMIBComplianceRev4 MODULE-COMPLIANCE
    STATUS          deprecated
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkTimerGroup,
                        ciscoGspLinkRemoteIpGroup,
                        ciscoGspLinkUtilGroup,
                        ciscoGspNotificationsEnableGroup,
                        ciscoGspNotificationsGroup,
                        ciscoGspLinkGroupRev1,
                        ciscoGspNotificationsEnableGroupSup1,
                        ciscoGspNotificationsGroupSup1,
                        ciscoGspLinkGroupSup1,
                        ciscoGspScalarsGroupSup1,
                        ciscoGspInstUPUGroup,
                        ciscoGspNotificationsInfoGroup,
                        ciscoGspNotificationsEnableGroupSup2,
                        ciscoGspNotificationsGroupSup2,
                        ciscoGspInstSccpWrrGroup
                    }

    OBJECT          cgspCLLICode
    MIN-ACCESS      read-only
    DESCRIPTION
        "Create/Write access is not required."

    OBJECT          cgspUtilSampleInterval
    MIN-ACCESS      read-only
    DESCRIPTION
        "Create/Write access is not required."

    OBJECT          cgspUtilThreshold
    MIN-ACCESS      read-only
    DESCRIPTION
        "Create/Write access is not required."

    OBJECT          cgspUtilAbateDelta
    MIN-ACCESS      read-only
    DESCRIPTION
        "Create/Write access is not required."

    OBJECT          cgspPlanCapacityDefault
    MIN-ACCESS      read-only
    DESCRIPTION
        "Create/Write access is not required."

    OBJECT          cgspProfileVariant
    MIN-ACCESS      read-only
    DESCRIPTION
        "Create/Write access is not required."

    OBJECT          cgspProfileMtp2BundleTimer
    MIN-ACCESS      read-only
    DESCRIPTION
        "Create/Write access is not required."

    OBJECT          cgspProfileMtp2SendQueueDepth
    MIN-ACCESS      read-only
    DESCRIPTION
        "Create/Write access is not required."

    OBJECT          cgspProfileRowStatus
    MIN-ACCESS      read-only
    DESCRIPTION
        "Create/Write access is not required."

    OBJECT          cgspProfileTimerValue
    MIN-ACCESS      read-only
    DESCRIPTION
        "Create/Write access is not required."

    OBJECT          cgspProfileTimerRowStatus
    MIN-ACCESS      read-only
    DESCRIPTION
        "Create/Write access is not required."

    OBJECT          cgspInstNetworkIndicator
    MIN-ACCESS      read-only
    DESCRIPTION
        "Create/Write access is not required."

    OBJECT          cgspInstVariant
    MIN-ACCESS      read-only
    DESCRIPTION
        "Create/Write access is not required."

    OBJECT          cgspInstDisplayName
    MIN-ACCESS      read-only
    DESCRIPTION
        "Create/Write access is not required."

    OBJECT          cgspInstDescription
    MIN-ACCESS      read-only
    DESCRIPTION
        "Create/Write access is not required."

    OBJECT          cgspInstTFR
    MIN-ACCESS      read-only
    DESCRIPTION
        "Create/Write access is not required."

    OBJECT          cgspInstCongestionsLevels
    MIN-ACCESS      read-only
    DESCRIPTION
        "Create/Write access is not required."

    OBJECT          cgspInstFastRestart
    MIN-ACCESS      read-only
    DESCRIPTION
        "Create/Write access is not required."

    OBJECT          cgspInstDistSccpUnseq
    MIN-ACCESS      read-only
    DESCRIPTION
        "Create/Write access is not required."

    OBJECT          cgspInstSummaryRoutingException
    MIN-ACCESS      read-only
    DESCRIPTION
        "Create/Write access is not required."

    OBJECT          cgspInstRouteTableName
    MIN-ACCESS      read-only
    DESCRIPTION
        "Create/Write access is not required."

    OBJECT          cgspInstRowStatus
    MIN-ACCESS      read-only
    DESCRIPTION
        "Create/Write access is not required."

    OBJECT          cgspInstTimerValue
    MIN-ACCESS      read-only
    DESCRIPTION
        "Create/Write access is not required."

    OBJECT          cgspInstTimerRowStatus
    MIN-ACCESS      read-only
    DESCRIPTION
        "Create/Write access is not required."

    OBJECT          cgspPointCodeType
    MIN-ACCESS      read-only
    DESCRIPTION
        "Create/Write access is not required."

    OBJECT          cgspPointCodeRowStatus
    MIN-ACCESS      read-only
    DESCRIPTION
        "Create/Write access is not required."

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinksetDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinkDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."
    ::= { ciscoGspMIBCompliances 5 }

ciscoGspMIBComplianceRev5 MODULE-COMPLIANCE
    STATUS          current
    DESCRIPTION
        "The compliance statement for entities which implement
        the CISCO-ITP-GSP-MIB"
    MODULE          -- this module
    MANDATORY-GROUPS {
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkTimerGroup,
                        ciscoGspLinkRemoteIpGroup,
                        ciscoGspLinkUtilGroup,
                        ciscoGspNotificationsEnableGroup,
                        ciscoGspNotificationsGroup,
                        ciscoGspLinkGroupRev1,
                        ciscoGspNotificationsEnableGroupSup1,
                        ciscoGspNotificationsGroupSup1,
                        ciscoGspLinkGroupSup1,
                        ciscoGspScalarsGroupSup1,
                        ciscoGspInstUPUGroup,
                        ciscoGspNotificationsInfoGroup,
                        ciscoGspNotificationsEnableGroupSup2,
                        ciscoGspNotificationsGroupSup2,
                        ciscoGspInstSccpWrrGroup,
                        ciscoGspLinkTableEntryGroupSup1,
                        ciscoGspNotificationsGroupSup3
                    }

    OBJECT          cgspCLLICode
    MIN-ACCESS      read-only
    DESCRIPTION
        "Create/Write access is not required"

    OBJECT          cgspUtilSampleInterval
    MIN-ACCESS      read-only
    DESCRIPTION
        "Create/Write access is not required"

    OBJECT          cgspUtilThreshold
    MIN-ACCESS      read-only
    DESCRIPTION
        "Create/Write access is not required"

    OBJECT          cgspUtilAbateDelta
    MIN-ACCESS      read-only
    DESCRIPTION
        "Create/Write access is not required"

    OBJECT          cgspPlanCapacityDefault
    MIN-ACCESS      read-only
    DESCRIPTION
        "Create/Write access is not required"

    OBJECT          cgspProfileVariant
    MIN-ACCESS      read-only
    DESCRIPTION
        "Create/Write access is not required"

    OBJECT          cgspProfileMtp2BundleTimer
    MIN-ACCESS      read-only
    DESCRIPTION
        "Create/Write access is not required"

    OBJECT          cgspProfileMtp2SendQueueDepth
    MIN-ACCESS      read-only
    DESCRIPTION
        "Create/Write access is not required"

    OBJECT          cgspProfileRowStatus
    MIN-ACCESS      read-only
    DESCRIPTION
        "Create/Write access is not required"

    OBJECT          cgspProfileTimerValue
    MIN-ACCESS      read-only
    DESCRIPTION
        "Create/Write access is not required"

    OBJECT          cgspProfileTimerRowStatus
    MIN-ACCESS      read-only
    DESCRIPTION
        "Create/Write access is not required"

    OBJECT          cgspInstNetworkIndicator
    MIN-ACCESS      read-only
    DESCRIPTION
        "Create/Write access is not required"

    OBJECT          cgspInstVariant
    MIN-ACCESS      read-only
    DESCRIPTION
        "Create/Write access is not required"

    OBJECT          cgspInstDisplayName
    MIN-ACCESS      read-only
    DESCRIPTION
        "Create/Write access is not required"

    OBJECT          cgspInstDescription
    MIN-ACCESS      read-only
    DESCRIPTION
        "Create/Write access is not required"

    OBJECT          cgspInstTFR
    MIN-ACCESS      read-only
    DESCRIPTION
        "Create/Write access is not required"

    OBJECT          cgspInstCongestionsLevels
    MIN-ACCESS      read-only
    DESCRIPTION
        "Create/Write access is not required"

    OBJECT          cgspInstFastRestart
    MIN-ACCESS      read-only
    DESCRIPTION
        "Create/Write access is not required"

    OBJECT          cgspInstDistSccpUnseq
    MIN-ACCESS      read-only
    DESCRIPTION
        "Create/Write access is not required"

    OBJECT          cgspInstSummaryRoutingException
    MIN-ACCESS      read-only
    DESCRIPTION
        "Create/Write access is not required"

    OBJECT          cgspInstRouteTableName
    MIN-ACCESS      read-only
    DESCRIPTION
        "Create/Write access is not required"

    OBJECT          cgspInstRowStatus
    MIN-ACCESS      read-only
    DESCRIPTION
        "Create/Write access is not required"

    OBJECT          cgspInstTimerValue
    MIN-ACCESS      read-only
    DESCRIPTION
        "Create/Write access is not required"

    OBJECT          cgspInstTimerRowStatus
    MIN-ACCESS      read-only
    DESCRIPTION
        "Create/Write access is not required"

    OBJECT          cgspPointCodeType
    MIN-ACCESS      read-only
    DESCRIPTION
        "Create/Write access is not required"

    OBJECT          cgspPointCodeRowStatus
    MIN-ACCESS      read-only
    DESCRIPTION
        "Create/Write access is not required"

    OBJECT          cgspLinksetSourcePointCode
    MIN-ACCESS      read-only
    DESCRIPTION
        "Create/Write access is not required."

    OBJECT          cgspLinksetAdjacentPointCode
    MIN-ACCESS      read-only
    DESCRIPTION
        "Create/Write access is not required."

    OBJECT          cgspLinksetInboundAcl
    MIN-ACCESS      read-only
    DESCRIPTION
        "Create/Write access is not required."

    OBJECT          cgspLinksetOutboundAcl
    MIN-ACCESS      read-only
    DESCRIPTION
        "Create/Write access is not required."

    OBJECT          cgspLinksetAccountingMtp3
    MIN-ACCESS      read-only
    DESCRIPTION
        "Create/Write access is not required."

    OBJECT          cgspLinksetAccountingGtt
    MIN-ACCESS      read-only
    DESCRIPTION
        "Create/Write access is not required."

    OBJECT          cgspLinksetActPriority
    MIN-ACCESS      read-only
    DESCRIPTION
        "Create/Write access is not required."

    OBJECT          cgspLinksetDisplayName
    MIN-ACCESS      read-only
    DESCRIPTION
        "Create/Write access is not required."

    OBJECT          cgspLinkDescription
    MIN-ACCESS      read-only
    DESCRIPTION
        "Create/Write access is not required."

    OBJECT          cgspLinksetRotateSlsEnable
    MIN-ACCESS      read-only
    DESCRIPTION
        "Create/Write access is not required."

    OBJECT          cgspLinksetRotateSlsShift
    MIN-ACCESS      read-only
    DESCRIPTION
        "Create/Write access is not required."

    OBJECT          cgspLinksetProfileName
    MIN-ACCESS      read-only
    DESCRIPTION
        "Create/Write access is not required."

    OBJECT          cgspLinksetRowStatus
    MIN-ACCESS      read-only
    DESCRIPTION
        "Create/Write access is not required."

    OBJECT          cgspLinksetTimerValue
    MIN-ACCESS      read-only
    DESCRIPTION
        "Create/Write access is not required."

    OBJECT          cgspLinksetTimerRowStatus
    MIN-ACCESS      read-only
    DESCRIPTION
        "Create/Write access is not required."

    OBJECT          cgspLinksetDescription
    MIN-ACCESS      read-only
    DESCRIPTION
        "Create/Write access is not required."

    OBJECT          cgspLinkType
    MIN-ACCESS      read-only
    DESCRIPTION
        "Create/Write access is not required."

    OBJECT          cgspLinkifIndex
    MIN-ACCESS      read-only
    DESCRIPTION
        "Create/Write access is not required."

    OBJECT          cgspLinkXmitQueueDepthHigh
    MIN-ACCESS      read-only
    DESCRIPTION
        "Create/Write access is not required."

    OBJECT          cgspLinkCongestionAbate1
    MIN-ACCESS      read-only
    DESCRIPTION
        "Create/Write access is not required."

    OBJECT          cgspLinkCongestionAbate2
    MIN-ACCESS      read-only
    DESCRIPTION
        "Create/Write access is not required."

    OBJECT          cgspLinkCongestionAbate3
    MIN-ACCESS      read-only
    DESCRIPTION
        "Create/Write access is not required."

    OBJECT          cgspLinkCongestionOnset1
    MIN-ACCESS      read-only
    DESCRIPTION
        "Create/Write access is not required."

    OBJECT          cgspLinkCongestionOnset2
    MIN-ACCESS      read-only
    DESCRIPTION
        "Create/Write access is not required."

    OBJECT          cgspLinkCongestionOnset3
    MIN-ACCESS      read-only
    DESCRIPTION
        "Create/Write access is not required."

    OBJECT          cgspLinkSigLinkTest
    MIN-ACCESS      read-only
    DESCRIPTION
        "Create/Write access is not required."

    OBJECT          cgspLinkLocalPeerPort
    MIN-ACCESS      read-only
    DESCRIPTION
        "Create/Write access is not required."

    OBJECT          cgspLinkRemotePeerPort
    MIN-ACCESS      read-only
    DESCRIPTION
        "Create/Write access is not required."

    OBJECT          cgspLinkQosClass
    MIN-ACCESS      read-only
    DESCRIPTION
        "Create/Write access is not required."

    OBJECT          cgspLinkDisplayName
    MIN-ACCESS      read-only
    DESCRIPTION
        "Create/Write access is not required."

    OBJECT          cgspLinkPlanCapacityRcvd
    MIN-ACCESS      read-only
    DESCRIPTION
        "Create/Write access is not required."

    OBJECT          cgspLinkUtilThresholdRcvd
    MIN-ACCESS      read-only
    DESCRIPTION
        "Create/Write access is not required."

    OBJECT          cgspLinkPlanCapacitySent
    MIN-ACCESS      read-only
    DESCRIPTION
        "Create/Write access is not required."

    OBJECT          cgspLinkUtilThresholdSent
    MIN-ACCESS      read-only
    DESCRIPTION
        "Create/Write access is not required."

    OBJECT          cgspLinkRowStatus
    MIN-ACCESS      read-only
    DESCRIPTION
        "Create/Write access is not required."

    OBJECT          cgspLinkTimerValue
    MIN-ACCESS      read-only
    DESCRIPTION
        "Create/Write access is not required."

    OBJECT          cgspLinkTimerRowStatus
    MIN-ACCESS      read-only
    DESCRIPTION
        "Create/Write access is not required."

    OBJECT          cgspLinkRemoteIpAddrType
    MIN-ACCESS      read-only
    DESCRIPTION
        "Create/Write access is not required."

    OBJECT          cgspLinkRemoteIpAddress
    MIN-ACCESS      read-only
    DESCRIPTION
        "Create/Write access is not required."

    OBJECT          cgspLinkRemoteIpAddrRowStatus
    MIN-ACCESS      read-only
    DESCRIPTION
        "Create/Write access is not required."

    OBJECT          cgspLinkRxCongestionState
    MIN-ACCESS      read-only
    DESCRIPTION
        "Create/Write access is not required."
    ::= { ciscoGspMIBCompliances 6 }

-- Units of Conformance

ciscoGspScalarsGroup OBJECT-GROUP
    OBJECTS         {
                        cgspCLLICode,
                        cgspUtilSampleInterval,
                        cgspUtilThreshold,
                        cgspUtilAbateDelta,
                        cgspPlanCapacityDefault,
                        cgspEventSequenceNumber
                    }
    STATUS          current
    DESCRIPTION
        "Scalars Group for Gateway Signalling Point."
    ::= { ciscoGspMIBGroups 1 }

ciscoGspProfileGroup OBJECT-GROUP
    OBJECTS         {
                        cgspProfileVariant,
                        cgspProfileMtp2BundleTimer,
                        cgspProfileMtp2SendQueueDepth,
                        cgspProfileRowStatus,
                        cgspProfileTimerValue,
                        cgspProfileTimerRowStatus
                    }
    STATUS          current
    DESCRIPTION
        "Profile Group for Gateway Signalling Point."
    ::= { ciscoGspMIBGroups 2 }

ciscoGspInstanceGroup OBJECT-GROUP
    OBJECTS         {
                        cgspInstNetworkIndicator,
                        cgspInstVariant,
                        cgspInstDisplayName,
                        cgspInstDescription,
                        cgspInstTFR,
                        cgspInstCongestionsLevels,
                        cgspInstFastRestart,
                        cgspInstDistSccpUnseq,
                        cgspInstSummaryRoutingException,
                        cgspInstNumber,
                        cgspInstRouteTableName,
                        cgspInstRowStatus
                    }
    STATUS          current
    DESCRIPTION
        "Instance of Signalling Point."
    ::= { ciscoGspMIBGroups 3 }

ciscoGspInstTimerGroup OBJECT-GROUP
    OBJECTS         {
                        cgspInstTimerValue,
                        cgspInstTimerRowStatus
                    }
    STATUS          current
    DESCRIPTION
        "Timers defined for each Instance of Signalling
        Point."
    ::= { ciscoGspMIBGroups 4 }

ciscoGspPointCodeGroup OBJECT-GROUP
    OBJECTS         {
                        cgspPointCodeType,
                        cgspPointCodeDisplay,
                        cgspPointCodeRowStatus
                    }
    STATUS          current
    DESCRIPTION
        "Pointcode defined for each Instance of
        Signalling Point."
    ::= { ciscoGspMIBGroups 5 }

ciscoGspLinksetGroup OBJECT-GROUP
    OBJECTS         {
                        cgspLinksetSourcePointCode,
                        cgspLinksetSourceDisplayPC,
                        cgspLinksetAdjacentPointCode,
                        cgspLinksetAdjacentDisplayPC,
                        cgspLinksetState,
                        cgspLinksetInboundAcl,
                        cgspLinksetOutboundAcl,
                        cgspLinksetAccountingMtp3,
                        cgspLinksetAccountingGtt,
                        cgspLinksetNumLinks,
                        cgspLinksetDurationInService,
                        cgspLinksetDurationOutService,
                        cgspLinksetActPriority,
                        cgspLinksetDisplayName,
                        cgspLinksetDescription,
                        cgspLinksetRotateSlsEnable,
                        cgspLinksetRotateSlsShift,
                        cgspLinksetProfileName,
                        cgspLinksetAdjacentInst,
                        cgspLinksetRowStatus
                    }
    STATUS          current
    DESCRIPTION
        "linkset objects ."
    ::= { ciscoGspMIBGroups 6 }

ciscoGspLinksetTimerGroup OBJECT-GROUP
    OBJECTS         {
                        cgspLinksetTimerValue,
                        cgspLinksetTimerRowStatus
                    }
    STATUS          current
    DESCRIPTION
        "Timers defined for each Linkset."
    ::= { ciscoGspMIBGroups 7 }

ciscoGspLinkGroup OBJECT-GROUP
    OBJECTS         {
                        cgspLinkDescription,
                        cgspLinkState,
                        cgspLinkReason,
                        cgspLinkType,
                        cgspLinkifIndex,
                        cgspLinkSctpAssociation,
                        cgspLinkXmitQueueDepth,
                        cgspLinkXmitQueueDepthHigh,
                        cgspLinkXmitQueueDepthHighRT,
                        cgspLinkCongestionState,
                        cgspLinkCongestionAbate1,
                        cgspLinkCongestionAbate2,
                        cgspLinkCongestionAbate3,
                        cgspLinkCongestionOnset1,
                        cgspLinkCongestionOnset2,
                        cgspLinkCongestionOnset3,
                        cgspLinkSigLinkTest,
                        cgspLinkQ752T1E1,
                        cgspLinkQ752T1E2,
                        cgspLinkQ752T1E3,
                        cgspLinkQ752T1E5,
                        cgspLinkQ752T1E7,
                        cgspLinkQ752T1E8,
                        cgspLinkQ752T1E9,
                        cgspLinkQ752T1E10,
                        cgspLinkQ752T1E11,
                        cgspLinkQ752T2E1,
                        cgspLinkQ752T2E5,
                        cgspLinkQ752T2E6,
                        cgspLinkQ752T2E7,
                        cgspLinkQ752T2E9,
                        cgspLinkQ752T2E10,
                        cgspLinkQ752T2E15,
                        cgspLinkQ752T2E16,
                        cgspLinkQ752T2E18,
                        cgspLinkQ752T3E1,
                        cgspLinkQ752T3E2Packets,
                        cgspLinkQ752T3E2Bytes,
                        cgspLinkQ752T3E3,
                        cgspLinkQ752T3E4,
                        cgspLinkQ752T3E5,
                        cgspLinkQ752T3E6,
                        cgspLinkQ752T3E7,
                        cgspLinkQ752T3E10L1,
                        cgspLinkQ752T3E10L2,
                        cgspLinkQ752T3E10L3,
                        cgspLinkQ752T3E11L1,
                        cgspLinkQ752T3E11L2,
                        cgspLinkQ752T3E11L3,
                        cgspLinkLocalPeerPort,
                        cgspLinkRemotePeerPort,
                        cgspLinkQosClass,
                        cgspLinkDisplayName,
                        cgspLinkDroppedPkts,
                        cgspLinkTransmittedLSSUs,
                        cgspLinkReceivedLSSUs,
                        cgspLinkProtocolDetails,
                        cgspLinkLsacState,
                        cgspLinkTsrcState,
                        cgspLinkTcocState,
                        cgspLinkTcocLocalBSNT,
                        cgspLinkTcocRemoteBSNT,
                        cgspLinkTcbcState,
                        cgspLinkReceivedSIBs,
                        cgspLinkTransmittedSIBs,
                        cgspLinkMtp2T01Counts,
                        cgspLinkMtp2T02Counts,
                        cgspLinkMtp2T03Counts,
                        cgspLinkMtp2T04Counts,
                        cgspLinkMtp2T05Counts,
                        cgspLinkMtp2T06Counts,
                        cgspLinkMtp2T07Counts,
                        cgspLinkOMAERMCounts,
                        cgspLinkOMAERMFailCounts,
                        cgspLinkOMSURMCounts,
                        cgspLinkOMSURMFailCounts,
                        cgspLinkPlanCapacityRcvd,
                        cgspLinkUtilThresholdRcvd,
                        cgspLinkUtilizationRcvd,
                        cgspLinkUtilStateRcvd,
                        cgspLinkL2BytesRcvd,
                        cgspLinkPlanCapacitySent,
                        cgspLinkUtilThresholdSent,
                        cgspLinkUtilizationSent,
                        cgspLinkUtilStateSent,
                        cgspLinkL2BytesSent,
                        cgspLinkTestResult,
                        cgspLinkRowStatus
                    }
    STATUS          deprecated
    DESCRIPTION
        "SP link objects."
    ::= { ciscoGspMIBGroups 8 }

ciscoGspLinkTimerGroup OBJECT-GROUP
    OBJECTS         {
                        cgspLinkTimerValue,
                        cgspLinkTimerRowStatus
                    }
    STATUS          current
    DESCRIPTION
        "Timers defined for each Link."
    ::= { ciscoGspMIBGroups 9 }

ciscoGspLinkRemoteIpGroup OBJECT-GROUP
    OBJECTS         {
                        cgspLinkRemoteIpAddrType,
                        cgspLinkRemoteIpAddress,
                        cgspLinkRemoteIpAddrRowStatus
                    }
    STATUS          current
    DESCRIPTION
        "Remote IP addresses for each Link."
    ::= { ciscoGspMIBGroups 10 }

ciscoGspLinkUtilGroup OBJECT-GROUP
    OBJECTS         {
                        cgspLinkUtilRcvd,
                        cgspLinkUtilSent,
                        cgspLinkUtilEndTimestamp
                    }
    STATUS          current
    DESCRIPTION
        "Utilization history for each Link."
    ::= { ciscoGspMIBGroups 11 }

ciscoGspNotificationsEnableGroup OBJECT-GROUP
    OBJECTS         {
                        cgspLsStateChangeNotifEnabled,
                        cgspLnkStateChangeNotifEnabled,
                        cgspCongestionNotifEnabled,
                        cgspLinkUtilNotifEnabled
                    }
    STATUS          current
    DESCRIPTION
        "SP enable notification objects."
    ::= { ciscoGspMIBGroups 12 }

ciscoGspNotificationsGroup NOTIFICATION-GROUP
   NOTIFICATIONS    {
                        ciscoGspLinksetStateChange,
                        ciscoGspLinkStateChange,
                        ciscoGspCongestionChange,
                        ciscoGspLinkRcvdUtilChange,
                        ciscoGspLinkSentUtilChange
                    }
    STATUS          current
    DESCRIPTION
        "SP notifications."
    ::= { ciscoGspMIBGroups 13 }

ciscoGspLinkGroupRev1 OBJECT-GROUP
    OBJECTS         {
                        cgspLinkDescription,
                        cgspLinkState,
                        cgspLinkReason,
                        cgspLinkType,
                        cgspLinkifIndex,
                        cgspLinkXmitQueueDepth,
                        cgspLinkXmitQueueDepthHigh,
                        cgspLinkXmitQueueDepthHighRT,
                        cgspLinkCongestionState,
                        cgspLinkCongestionAbate1,
                        cgspLinkCongestionAbate2,
                        cgspLinkCongestionAbate3,
                        cgspLinkCongestionOnset1,
                        cgspLinkCongestionOnset2,
                        cgspLinkCongestionOnset3,
                        cgspLinkSigLinkTest,
                        cgspLinkQ752T1E1,
                        cgspLinkQ752T1E2,
                        cgspLinkQ752T1E3,
                        cgspLinkQ752T1E5,
                        cgspLinkQ752T1E7,
                        cgspLinkQ752T1E8,
                        cgspLinkQ752T1E9,
                        cgspLinkQ752T1E10,
                        cgspLinkQ752T1E11,
                        cgspLinkQ752T2E1,
                        cgspLinkQ752T2E5,
                        cgspLinkQ752T2E6,
                        cgspLinkQ752T2E7,
                        cgspLinkQ752T2E9,
                        cgspLinkQ752T2E10,
                        cgspLinkQ752T2E15,
                        cgspLinkQ752T2E16,
                        cgspLinkQ752T2E18,
                        cgspLinkQ752T3E1,
                        cgspLinkQ752T3E2Packets,
                        cgspLinkQ752T3E2Bytes,
                        cgspLinkQ752T3E3,
                        cgspLinkQ752T3E4,
                        cgspLinkQ752T3E5,
                        cgspLinkQ752T3E6,
                        cgspLinkQ752T3E7,
                        cgspLinkQ752T3E10L1,
                        cgspLinkQ752T3E10L2,
                        cgspLinkQ752T3E10L3,
                        cgspLinkQ752T3E11L1,
                        cgspLinkQ752T3E11L2,
                        cgspLinkQ752T3E11L3,
                        cgspLinkLocalPeerPort,
                        cgspLinkRemotePeerPort,
                        cgspLinkQosClass,
                        cgspLinkDisplayName,
                        cgspLinkDroppedPkts,
                        cgspLinkTransmittedLSSUs,
                        cgspLinkReceivedLSSUs,
                        cgspLinkProtocolDetails,
                        cgspLinkLsacState,
                        cgspLinkTsrcState,
                        cgspLinkTcocState,
                        cgspLinkTcocLocalBSNT,
                        cgspLinkTcocRemoteBSNT,
                        cgspLinkTcbcState,
                        cgspLinkReceivedSIBs,
                        cgspLinkTransmittedSIBs,
                        cgspLinkMtp2T01Counts,
                        cgspLinkMtp2T02Counts,
                        cgspLinkMtp2T03Counts,
                        cgspLinkMtp2T04Counts,
                        cgspLinkMtp2T05Counts,
                        cgspLinkMtp2T06Counts,
                        cgspLinkMtp2T07Counts,
                        cgspLinkOMAERMCounts,
                        cgspLinkOMAERMFailCounts,
                        cgspLinkOMSURMCounts,
                        cgspLinkOMSURMFailCounts,
                        cgspLinkPlanCapacityRcvd,
                        cgspLinkUtilThresholdRcvd,
                        cgspLinkUtilizationRcvd,
                        cgspLinkUtilStateRcvd,
                        cgspLinkL2BytesRcvd,
                        cgspLinkPlanCapacitySent,
                        cgspLinkUtilThresholdSent,
                        cgspLinkUtilizationSent,
                        cgspLinkUtilStateSent,
                        cgspLinkL2BytesSent,
                        cgspLinkTestResult,
                        cgspLinkRowStatus,
                        cgspLinkSctpAssociationId
                    }
    STATUS          current
    DESCRIPTION
        "SP link objects."
    ::= { ciscoGspMIBGroups 14 }

ciscoGspNotificationsEnableGroupSup1 OBJECT-GROUP
    OBJECTS         { cgspIsolationNotifEnabled }
    STATUS          current
    DESCRIPTION
        "Isolation notification enable."
    ::= { ciscoGspMIBGroups 15 }

ciscoGspNotificationsGroupSup1 NOTIFICATION-GROUP
   NOTIFICATIONS    { ciscoGspIsolation }
    STATUS          current
    DESCRIPTION
        "Isolation notification."
    ::= { ciscoGspMIBGroups 16 }

ciscoGspLinkGroupSup1 OBJECT-GROUP
    OBJECTS         {
                        cgspLinkQ752T1E12,
                        cgspLinkQ752T1E12Errors,
                        cgspLinkQ752T2E11,
                        cgspLinkQ752T2E17,
                        cgspLinkQ752T2E19
                    }
    STATUS          current
    DESCRIPTION
        "Additional Link statistics."
    ::= { ciscoGspMIBGroups 17 }

ciscoGspScalarsGroupSup1 OBJECT-GROUP
    OBJECTS         { cgspUPUNotifWindowTime }
    STATUS          current
    DESCRIPTION
        "Scalar Group supplements."
    ::= { ciscoGspMIBGroups 18 }

ciscoGspInstUPUGroup OBJECT-GROUP
    OBJECTS         {
                        cgspInstSIUPUReceived,
                        cgspInstSIUPUTransmitted,
                        cgspInstUserPartDisplay
                    }
    STATUS          current
    DESCRIPTION
        "SS7 Destination and Service Indicator group."
    ::= { ciscoGspMIBGroups 20 }

ciscoGspNotificationsInfoGroup OBJECT-GROUP
    OBJECTS         {
                        cgspUPUIntervalDuration,
                        cgspIntervalUPUs
                    }
    STATUS          current
    DESCRIPTION
        "Notifications Info Group."
    ::= { ciscoGspMIBGroups 21 }

ciscoGspNotificationsEnableGroupSup2 OBJECT-GROUP
    OBJECTS         { cgspUPUNotifEnabled }
    STATUS          current
    DESCRIPTION
        "UPU notifications enable."
    ::= { ciscoGspMIBGroups 22 }

ciscoGspNotificationsGroupSup2 NOTIFICATION-GROUP
   NOTIFICATIONS    {
                        ciscoGspUPUReceived,
                        ciscoGspUPUTransmitted
                    }
    STATUS          current
    DESCRIPTION
        "Adjacent SP accessibility notification,
        UPU sent and received notifications."
    ::= { ciscoGspMIBGroups 23 }

ciscoGspInstSccpWrrGroup OBJECT-GROUP
    OBJECTS         {
                        cgspInstSccpWrrOpcShift,
                        cgspInstSccpWrrOption
                    }
    STATUS          current
    DESCRIPTION
        "SCCP GTT weighted loadshare group."
    ::= { ciscoGspMIBGroups 24 }

ciscoGspLinkTableEntryGroupSup1 OBJECT-GROUP
    OBJECTS         { cgspLinkRxCongestionState }
    STATUS          current
    DESCRIPTION
        "cgspLinkRxCongestionstate object for
        Received side congestion"
    ::= { ciscoGspMIBGroups 25 }

ciscoGspNotificationsGroupSup3 NOTIFICATION-GROUP
   NOTIFICATIONS    { ciscoGspRxCongestionChange }
    STATUS          current
    DESCRIPTION
        "Link Receive side congestion notication."
    ::= { ciscoGspMIBGroups 26 }

END
