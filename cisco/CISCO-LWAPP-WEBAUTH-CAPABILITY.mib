-- *****************************************************************
-- CISCO-LWAPP-WEBAUTH-CAPABILITY.my:
-- CISCO-LWAPP-WEBAUTH-MIB CAPABILITIES
--
-- July 2010 -  Suja T
--
-- Copyright (c) 2006, 2010 by cisco Systems Inc.
-- All rights reserved.
--
-- *****************************************************************

CISCO-LWAPP-WEBAUTH-CAPABILITY DEFINITIONS ::= BEGIN

IMPORTS
    MODULE-IDENTITY
        FROM SNMPv2-SMI
    AGENT-CAPABILITIES
        FROM SNMPv2-CONF
    ciscoAgentCapability
        FROM CISCO-SMI;


ciscoLwappWebauthCapability MODULE-IDENTITY
    LAST-UPDATED    "201007300000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for
        CISCO-LWAPP-WEBAUTH-MIB."
    REVISION        "201007300000Z"
    DESCRIPTION
        "Latest version of this MIB module."
    ::= { ciscoAgentCapability 5555 }


ciscoLwappWebAuthCapabilityCUWNSV7R0 AGENT-CAPABILITIES
    PRODUCT-RELEASE "Cisco Unified Wireless Network Software
                        Release 7.0 for Cisco WLAN Controllers"
    STATUS          current
    DESCRIPTION
        "CiscoLwappWebAuthMIB capabilities"

    SUPPORTS        CISCO-LWAPP-WEBAUTH-MIB
    INCLUDES        { cLWACustomWebAuthGroup }
    VARIATION       cLWAProxyRedirectPortNumber
    DESCRIPTION
        "The supported range for the value is 0-65535."

    ::= { ciscoLwappWebauthCapability 1 }

END
