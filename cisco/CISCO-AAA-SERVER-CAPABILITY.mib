-- *****************************************************************
-- CISCO-AAA-SERVER-CAPABILITY.my:  Cisco AAA Server MIB AGENT-CAPABILITIES
--
-- November, 2003 - Mark W. Eklund, Sanjeev C Joshi
--
-- Copyright (c) 2000, 2003 by cisco Systems, Inc.
-- All rights reserved.
--
-- *****************************************************************

CISCO-AAA-SERVER-CAPABILITY DEFINITIONS ::= BEGIN


IMPORTS
        MODULE-IDENTITY
                FROM SNMPv2-SMI
        AGENT-CAPABILITIES
                FROM SNMPv2-CONF
        ciscoAgentCapability
                FROM CISCO-SMI;

ciscoAAAServerCapability MODULE-IDENTITY
        LAST-UPDATED    "200602210000Z"
        ORGANIZATION    "Cisco Systems, Inc."
        CONTACT-INFO
                "       Cisco Systems
                        Customer Service

                Postal: 170 W Tasman Drive
                        San Jose, CA  95134
                        USA

                   Tel: +1 800 553-NETS

                E-mail: cs-aaa@cisco.com"
        DESCRIPTION
                "Agent capabilities for CISCO-AAA-SERVER-MIB"

        REVISION  "200602210000Z"
        DESCRIPTION
                "Agent capabilities for Application 
                 Control Engine (ACE)."
                
        REVISION  "200311140000Z"
        DESCRIPTION
                "Agent capabilities for Cisco MDS 1.3."
                
        REVISION  "200001200000Z"
        DESCRIPTION
                "Initial version of this MIB."                
               
        ::= { ciscoAgentCapability 129 }

ciscoAAAServerCapabilityV10R00 AGENT-CAPABILITIES

PRODUCT-RELEASE "Cisco IOS 12.0(4)XJ"
        STATUS          current
        DESCRIPTION     "Cisco AAA Server MIB capabilities"

        SUPPORTS        CISCO-AAA-SERVER-MIB
        INCLUDES        {casStatisticsGroup,
                         casConfigGroup,
                         casServerNotificationGroup}

        VARIATION           casConfigEntry
        CREATION-REQUIRES   { casAddress }
        DESCRIPTION         "The address must be specified during 
                             creation"

        VARIATION       casAddress
        ACCESS          read-only
        DESCRIPTION     "create is not yet supported"

        VARIATION       casAuthenPort
        ACCESS          read-only
        DESCRIPTION     "create is not yet supported"

        VARIATION       casAcctPort
        ACCESS          read-only
        DESCRIPTION     "create is not yet supported"

        VARIATION       casKey
        ACCESS          read-only
        DESCRIPTION     "create is not yet supported"

        VARIATION       casConfigRowStatus
        ACCESS          read-only
        DESCRIPTION     "create is not yet supported"

::= { ciscoAAAServerCapability 1 }

ciscoAAAServerCapabilityMDS13R1 AGENT-CAPABILITIES

PRODUCT-RELEASE "Cisco MDS 1.3(1)"
        STATUS          current
        DESCRIPTION     "Cisco AAA Server MIB capabilities"

        SUPPORTS        CISCO-AAA-SERVER-MIB
        INCLUDES        { casConfigGroup }
        
        VARIATION       casServerStateChangeEnable
        ACCESS          not-implemented
        DESCRIPTION     "Not Supported."
        
        VARIATION       casAuthenPort
        DEFVAL          { 1812 }
        DESCRIPTION     "As per the IANA port assignments,
                         DEFVAL is 1812 for radius server and
                         DEFVAL is 49 for tacacs+ server."
                         
        VARIATION       casAcctPort
        DEFVAL          { 1813 }
        DESCRIPTION     "As per the IANA port assignments,
                         DEFVAL is 1813 for radius server. 
                         The value is ignored for tacacs+
                         server."        
        
        VARIATION       casPriority
        ACCESS          not-implemented
        DESCRIPTION     "Not relevant in MDS implementation."
        
        VARIATION       casConfigRowStatus
        DESCRIPTION     "Only allowed values are :
                         - 'createAndGo' 
                         - 'destroy'
                         - 'active'
                         ."
                         
        VARIATION       casProtocol
        DESCRIPTION     "The supported protcols are; 
                          - tacacsplus(1) - TACACS+
                          - radius(2)     - RADIUS
                        ." 
                        
::= { ciscoAAAServerCapability 2 }

ciscoAAAServerCapabilityACSWV03R000 AGENT-CAPABILITIES

PRODUCT-RELEASE         "ACSW (Application Control Software) 3.0"
        STATUS          current
        DESCRIPTION     "Cisco AAA Server MIB capabilities
                         for ACSW 3.0"

        SUPPORTS        CISCO-AAA-SERVER-MIB
        INCLUDES        { casConfigGroup }
        
        VARIATION       casServerStateChangeEnable
        ACCESS          read-only
        DESCRIPTION     "Create operation not supported"
        
        VARIATION       casAddress
        ACCESS          read-only
        DESCRIPTION     "Create operation not supported"

        VARIATION       casAuthenPort
        ACCESS          read-only
        DEFVAL          { 1812 }
        DESCRIPTION     "As per the IANA port assignments,
                         DEFVAL is 1812 for radius server and
                         DEFVAL is 49 for tacacs+ server.
                         Create operation not supported"
                         
        VARIATION       casAcctPort
        ACCESS          read-only
        DEFVAL          { 1813 }
        DESCRIPTION     "As per the IANA port assignments,
                         DEFVAL is 1813 for radius server. 
                         The value is ignored for tacacs+
                         server. 
                         Create operation not supported."        
        
        VARIATION       casPriority
        ACCESS          not-implemented
        DESCRIPTION     "Not supported."
        
        VARIATION       casConfigRowStatus
        ACCESS          read-only
        DESCRIPTION     "Create operation not supported"
                         
::= { ciscoAAAServerCapability 3 }

END
