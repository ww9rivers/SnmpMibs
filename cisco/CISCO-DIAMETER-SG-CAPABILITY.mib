-- *****************************************************************
-- CISCO-DIAMETER-SG-CAPABILITY.my:  Cisco Diameter Server Group MIB
-- AGENT-CAPABILITIES
--
-- September 07, 2006 - Subash T.Comerica
--
-- Copyright (c) 2006 by Cisco Systems, Inc.
-- All rights reserved.
--
-- *****************************************************************

CISCO-DIAMETER-SG-CAPABILITY DEFINITIONS ::= BEGIN

IMPORTS
    MODULE-IDENTITY
        FROM SNMPv2-SMI
    AGENT-CAPABILITIES
        FROM SNMPv2-CONF
    ciscoAgentCapability
        FROM CISCO-SMI;


ciscoDiameterSGCapability MODULE-IDENTITY
    LAST-UPDATED    "200609070000Z"
    ORGANIZATION    "Cisco Systems, Inc."
    CONTACT-INFO
            "Cisco Systems
            Customer Service

            Postal: 170 W Tasman Drive
            San Jose, CA  95134
            USA

            Tel: +1 800 553-NETS

            E-mail: cs-aaa@cisco.com"
    DESCRIPTION
            "The capabilities description of
            CISCO-DIAMETER-SG-MIB."
    REVISION        "200609070000Z"
    DESCRIPTION
            "Initial version of this MIB module."
          ::= { ciscoAgentCapability 518 }



ciscoDiameterSGCapabilityV12R0409XG AGENT-CAPABILITIES
    PRODUCT-RELEASE "Cisco IOS 12.4(9)XG."
    STATUS          current
    DESCRIPTION     "Cisco Diameter Server Group MIB capabilities"

    SUPPORTS        CISCO-DIAMETER-SG-MIB
    INCLUDES        { ciscoDiameterSGHostCfgGroup }
    VARIATION       cdsgServerGroupRowStatus
    SYNTAX          INTEGER  {
                        active(1),
                        createAndGo(4),
                        destroy(6)
                    }
    ACCESS          read-create
    DESCRIPTION
            "Creation of new entries using createAndWait(5) and
                                                            suspension of entries using notInService(2) is not
                                                            supported."

    VARIATION       cdsgServerGroupStorageType
    ACCESS          read-only
    DESCRIPTION     "Write operation not allowed by SNMP."

    VARIATION       cdsgServerRowStatus
    SYNTAX          INTEGER  {
                        active(1),
                        createAndGo(4),
                        destroy(6)
                    }
    ACCESS          read-create
    DESCRIPTION
            "Creation of new entries using createAndWait(5) and
                                                            suspension of entries using notInService(2) is not
                                                            supported."

    VARIATION       cdsgServerStorageType
    ACCESS          read-only
    DESCRIPTION     "Write operation not allowed by SNMP."

    ::= { ciscoDiameterSGCapability 1 }

END
