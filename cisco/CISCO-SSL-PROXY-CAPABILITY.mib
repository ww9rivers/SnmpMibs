-- *****************************************************************
-- CISCO-SSL-PROXY-CAPABILITY.my: SSL Proxy Agent Capability MIB file
--
-- July 2003, Fatima Yu
--
-- Copyright (c) 2003, 2008 by cisco Systems Inc.
-- All rights reserved.
-- *****************************************************************

CISCO-SSL-PROXY-CAPABILITY DEFINITIONS ::= BEGIN

IMPORTS
    MODULE-IDENTITY
        FROM SNMPv2-SMI
    AGENT-CAPABILITIES
        FROM SNMPv2-CONF
    ciscoAgentCapability
        FROM CISCO-SMI;


ciscoSslProxyCapability MODULE-IDENTITY
    LAST-UPDATED    "200804080000Z"
    ORGANIZATION    "Cisco Systems, Inc."
    CONTACT-INFO
            "Cisco Systems
            Customer Service

            Postal: 170 West Tasman Drive
            San Jose, CA  95134
            USA

            Tel:    +1 800 553-NETS

            E-mail: cs-snmp@cisco.com, cs-ssl@cisco.com"
    DESCRIPTION
        "Agent capabilities for the CISCO-SSL-PROXY-MIB"
    REVISION        "200804080000Z"
    DESCRIPTION
        "Initial version of this MIB module."
    ::= { ciscoAgentCapability 364 }



ciscoSslProxyCapCat6KV02R01 AGENT-CAPABILITIES
    PRODUCT-RELEASE "Cisco Catalyst 6000 SSL Module Release 2.1"
    STATUS          current
    DESCRIPTION
        "MIB Agent Capability of Cisco Catalyst 6000 SSL Module
        Release 2.1"

    SUPPORTS        CISCO-SSL-PROXY-MIB
    INCLUDES        {
                        cspGlobalConfigGroup,
                        cspProxyServiceConfigGroup,
                        cspSslGroup,
                        cspSsl3Group,
                        cspTls1Group,
                        cspSslErrorGroup,
                        cspCpuStatusGroup,
                        cspProxyServiceNotificationGroup
                    }
    VARIATION       cspGcFIPSMode
    ACCESS          read-only
    DESCRIPTION
        "Write access is not supported"

    VARIATION       cspGcNotifyProxyServOperStatus
    ACCESS          read-only
    DESCRIPTION
        "Write access is not supported"

    VARIATION       cspGcNotifyPSCertExpiring
    ACCESS          read-only
    DESCRIPTION
        "Write access is not supported"

    VARIATION       cspGcPSCertExpireInterval
    ACCESS          read-only
    DESCRIPTION
        "Write access is not supported"

    VARIATION       cspPsServiceType
    ACCESS          read-only
    DESCRIPTION
        "Create/Write access is not supported"

    VARIATION       cspPsVirtualAddressType
    ACCESS          read-only
    DESCRIPTION
        "Create/Write access is not supported"

    VARIATION       cspPsVirtualAddress
    ACCESS          read-only
    DESCRIPTION
        "Create/Write access is not supported"

    VARIATION       cspPsVirtualPort
    ACCESS          read-only
    DESCRIPTION
        "Create/Write access is not supported"

    VARIATION       cspPsServerAddress
    ACCESS          read-only
    DESCRIPTION
        "Create/Write access is not supported"

    VARIATION       cspPsServerAddressType
    ACCESS          read-only
    DESCRIPTION
        "Create/Write access is not supported"

    VARIATION       cspPsServerPort
    ACCESS          read-only
    DESCRIPTION
        "Create/Write access is not supported"

    VARIATION       cspPsAdminStatus
    ACCESS          read-only
    DESCRIPTION
        "Create/Write access is not supported"

    VARIATION       cspPsConfigRowStatus
    ACCESS          not-implemented
    DESCRIPTION
        "This object is not supported"

    VARIATION       cspPspVirTcpPolicyName
    ACCESS          read-only
    DESCRIPTION
        "Create/Write access is not supported"

    VARIATION       cspPspSerTcpPolicyName
    ACCESS          read-only
    DESCRIPTION
        "Create/Write access is not supported"

    VARIATION       cspPspSslPolicyName
    ACCESS          read-only
    DESCRIPTION
        "Create/Write access is not supported"

    VARIATION       cspPspHttpHdrPolicyName
    ACCESS          read-only
    DESCRIPTION
        "Create/Write access is not supported"

    VARIATION       cspPspUrlRewritePolicyName
    ACCESS          read-only
    DESCRIPTION
        "Create/Write access is not supported"

    VARIATION       cspPskcTrustPointName
    ACCESS          read-only
    DESCRIPTION
        "Create/Write access is not supported"

    VARIATION       cspPskcCertFileName
    ACCESS          not-implemented
    DESCRIPTION
        "This object is not supported"

    VARIATION       cspPskcKeyName
    ACCESS          read-only
    DESCRIPTION
        "Create/Write access is not supported"

    VARIATION       cspPskcKeyFileName
    ACCESS          not-implemented
    DESCRIPTION
        "This object is not supported"

    VARIATION       cspPskcConfigRowStatus
    ACCESS          not-implemented
    DESCRIPTION
        "This object is not supported"

    ::= { ciscoSslProxyCapability 1 }

ciscoSslProxyCapACSWV03RA3006 AGENT-CAPABILITIES
    PRODUCT-RELEASE "ACSW (Application Control Software) 3.0(0)A3(0.0.6)"
    STATUS          current
    DESCRIPTION
        "ACSW (Application Control Software) 3.0(0)A3(0.0.6)
        CISCO-SSL-PROXY-MIB capabilities"

    SUPPORTS        CISCO-SSL-PROXY-MIB
    INCLUDES        {
                        cspSslGroup,
                        cspSsl3Group,
                        cspTls1Group
                    }
    VARIATION       cspScConnAttempt
    ACCESS          not-implemented
    DESCRIPTION
        "This object is not supported"

    VARIATION       cspScConnComplete
    ACCESS          not-implemented
    DESCRIPTION
        "This object is not supported"

    VARIATION       cspScRenegAttempt
    ACCESS          not-implemented
    DESCRIPTION
        "This object is not supported"

    VARIATION       cspScMaxHandShakeConns
    ACCESS          not-implemented
    DESCRIPTION
        "This object is not supported"

    VARIATION       cspScCurrDeviceQLen
    ACCESS          not-implemented
    DESCRIPTION
        "This object is not supported"

    VARIATION       cspScMaxDeviceQLen
    ACCESS          not-implemented
    DESCRIPTION
        "This object is not supported"

    VARIATION       cspScSessionReuses
    ACCESS          not-implemented
    DESCRIPTION
        "This object is not supported"

    VARIATION       cspS3cBadMacRcvd
    ACCESS          not-implemented
    DESCRIPTION
        "This object is not supported"

    VARIATION       cspS3cPadErrors
    ACCESS          not-implemented
    DESCRIPTION
        "This object is not supported"

    VARIATION       cspS3cRSArc4128md5
    ACCESS          not-implemented
    DESCRIPTION
        "This object is not supported"

    VARIATION       cspS3cRSArc4128sha
    ACCESS          not-implemented
    DESCRIPTION
        "This object is not supported"

    VARIATION       cspS3cRSAdescbcsha
    ACCESS          not-implemented
    DESCRIPTION
        "This object is not supported"

    VARIATION       cspS3cRSA3desedecbcsha
    ACCESS          not-implemented
    DESCRIPTION
        "This object is not supported"

    VARIATION       cspTlcBadMacRcvd
    ACCESS          not-implemented
    DESCRIPTION
        "This object is not supported"

    VARIATION       cspTlcPadErrors
    ACCESS          not-implemented
    DESCRIPTION
        "This object is not supported"

    VARIATION       cspTlcRSArc4128md5
    ACCESS          not-implemented
    DESCRIPTION
        "This object is not supported"

    VARIATION       cspTlcRSArc4128sha
    ACCESS          not-implemented
    DESCRIPTION
        "This object is not supported"

    VARIATION       cspTlcRSAdescbcsha
    ACCESS          not-implemented
    DESCRIPTION
        "This object is not supported"

    VARIATION       cspTlcRSA3desedecbcsha
    ACCESS          not-implemented
    DESCRIPTION
        "This object is not supported"

    ::= { ciscoSslProxyCapability 2 }

END
