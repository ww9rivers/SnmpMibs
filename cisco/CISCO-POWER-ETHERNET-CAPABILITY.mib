-- *****************************************************************
-- CISCO-POWER-ETHERNET-CAPABILITY.my:
-- Cisco POWER-ETHERNET-MIB AGENT-CAPABILITIES
--
-- June 2004, Seth Wang
--
-- Copyright (c) 2004, 2006-2007, 2009 by Cisco Systems Inc.
-- All rights reserved.
-- ****************************************************************

CISCO-POWER-ETHERNET-CAPABILITY DEFINITIONS ::= BEGIN

IMPORTS
    MODULE-IDENTITY
        FROM SNMPv2-SMI
    AGENT-CAPABILITIES
        FROM SNMPv2-CONF
    TruthValue
        FROM SNMPv2-TC
    ciscoAgentCapability
        FROM CISCO-SMI;


ciscoPowerEthernetCapability MODULE-IDENTITY
    LAST-UPDATED    "200902140000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        POWER-ETHERNET-MIB."
    REVISION        "200902140000Z"
    DESCRIPTION
        "Added capability statement
        cPowerEthernetCapV12RO252SGPCat4K."
    REVISION        "200707090000Z"
    DESCRIPTION
        "Added capability statement
        cPowerEthernetCapV12RO233SXHPCat6K."
    REVISION        "200702080000Z"
    DESCRIPTION
        "Added a new AGENT-CAPABILITIES cPowerEthernetCapC3kV122SR035 for
        c3550"
    REVISION        "200605310000Z"
    DESCRIPTION
        "Added the VARIATION for
        pethPsePortPowerPriority in
        cPowerEthernetCapCatOSV08R0401."
    REVISION        "200406280000Z"
    DESCRIPTION
        "Initial version of this MIB module."
    ::= { ciscoAgentCapability 412 }



cPowerEthernetCapCatOSV08R0401 AGENT-CAPABILITIES
    PRODUCT-RELEASE "Cisco CatOS 8.4(1)."
    STATUS          current
    DESCRIPTION
        "POWER-ETHERNET-MIB capabilities."

    SUPPORTS        POWER-ETHERNET-MIB
    INCLUDES        {
                        pethPsePortGroup,
                        pethPsePortNotificationGroup,
                        pethNotificationControlGroup,
                        pethMainPseGroup,
                        pethMainPowerNotificationGroup
                    }
    VARIATION       pethPsePortPowerPairsControlAbility
    SYNTAX          TruthValue
    DESCRIPTION
        "Only a limited set of enumerated values
        is supported."

    VARIATION       pethPsePortPowerPairs
    SYNTAX          INTEGER  {
                        signal(1)
                    }
    DESCRIPTION
        "Only a limited set of enumerated values
        is supported."

    VARIATION       pethPsePortType
    ACCESS          read-only
    DESCRIPTION
        "Unable to set this in CatOS."

    VARIATION       pethPsePortPowerPriority
    ACCESS          read-only
    DESCRIPTION
        "Unable to set this in CatOS."

    ::= { ciscoPowerEthernetCapability 1 }

cPowerEthernetCapC3kV122SR035 AGENT-CAPABILITIES
    PRODUCT-RELEASE "CISCO IOS 12.2S(0.35) for cat3k"
    STATUS          current
    DESCRIPTION
        "POWER-ETHERNET-MIB Capabilities"

    SUPPORTS        POWER-ETHERNET-MIB
    INCLUDES        {
                        pethPsePortGroup,
                        pethMainPseGroup,
                        pethNotificationControlGroup,
                        pethPsePortNotificationGroup,
                        pethMainPowerNotificationGroup
                    }
    VARIATION       pethPsePortPowerPairs
    ACCESS          read-only
    DESCRIPTION
        "Read-only access is supported."

    VARIATION       pethPsePortPowerPriority
    SYNTAX          INTEGER  {
                        high(2),
                        low(3)
                    }
    DESCRIPTION
        "Value Critical(1) is not supported on c3750/c3560/c3550 and
        Value High(2) is not supported on c3550"

    VARIATION       pethPsePortMPSAbsentCounter
    DESCRIPTION
        "Returns zero always."

    VARIATION       pethPsePortOverLoadCounter
    DESCRIPTION
        "Returns zero always."

    VARIATION       pethPsePortType
    ACCESS          read-only
    DESCRIPTION
        "Read-only access is supported."

    VARIATION       pethMainPseOperStatus
    SYNTAX          INTEGER  {
                        on(1),
                        off(2)
                    }
    DESCRIPTION
        "The value Faulty(3) is not supported on c3750/c3560/c3550."

    VARIATION       pethMainPseConsumptionPower
    DESCRIPTION
        "This gives total allocated power instead of total actual
        consumed power for c3750/c3560/c3550."

    ::= { ciscoPowerEthernetCapability 2 }

cPowerEthernetCapV12RO233SXHPCat6K AGENT-CAPABILITIES
    PRODUCT-RELEASE "Cisco IOS 12.2(33)SXH on Catalyst 6000/6500
                         series devices."
    STATUS          current
    DESCRIPTION
        "POWER-ETHERNET-MIB capabilities."

    SUPPORTS        POWER-ETHERNET-MIB
    INCLUDES        {
                        pethPsePortGroup,
                        pethPsePortNotificationGroup,
                        pethNotificationControlGroup,
                        pethMainPseGroup
                    }
    VARIATION       pethPsePortPowerPairsControlAbility
    SYNTAX          TruthValue {
                        false(2)
                    }
    DESCRIPTION
        "Only a limited set of enumerated values
        is supported."

    VARIATION       pethPsePortPowerPairs
    SYNTAX          INTEGER  {
                        signal(1)
                    }
    DESCRIPTION
        "Only a limited set of enumerated values
        is supported."

    VARIATION       pethPsePortType
    ACCESS          read-only
    DESCRIPTION
        "Unable to set this."

    VARIATION       pethPsePortPowerPriority
    ACCESS          read-only
    DESCRIPTION
        "Unable to set this."

    VARIATION       pethMainPseUsageThreshold
    DESCRIPTION
        "Not supported."

    ::= { ciscoPowerEthernetCapability 3 }

cPowerEthernetCapV12RO252SGPCat4K AGENT-CAPABILITIES
    PRODUCT-RELEASE "Cisco IOS 12.2(52)SG on CAT4K family
                    switches."
    STATUS          current
    DESCRIPTION
        "POWER-ETHERNET-MIB capabilities."

    SUPPORTS        POWER-ETHERNET-MIB
    INCLUDES        {
                        pethPsePortGroup,
                        pethPsePortNotificationGroup,
                        pethNotificationControlGroup,
                        pethMainPseGroup
                    }
    VARIATION       pethPsePortPowerPairs
    ACCESS          read-only
    DESCRIPTION
        "Unable to set this."

    VARIATION       pethPsePortType
    ACCESS          read-only
    DESCRIPTION
        "Unable to set this."

    VARIATION       pethPsePortPowerPriority
    ACCESS          read-only
    DESCRIPTION
        "Unable to set this."

    VARIATION       pethMainPseUsageThreshold
    ACCESS          not-implemented
    DESCRIPTION
        "Not supported."

    ::= { ciscoPowerEthernetCapability 4 }

END
