-- *****************************************************************
-- CISCO-ETHERLIKE-EXT-CAPABILITY.my
-- CISCO-ETHERLIKE-EXT-MIB agent capabilities
--   
-- March 2010, Guichuan Tang
--   
-- Copyright (c) 2010 by Cisco Systems, Inc.
-- All rights reserved.
-- *****************************************************************

CISCO-ETHERLIKE-EXT-CAPABILITY DEFINITIONS ::= BEGIN

IMPORTS
    MODULE-IDENTITY
        FROM SNMPv2-SMI
    AGENT-CAPABILITIES
        FROM SNMPv2-CONF
    ciscoAgentCapability
        FROM CISCO-SMI;


ciscoEtherlikeExtCapability MODULE-IDENTITY
    LAST-UPDATED    "201010290000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "Agent capabilities for CISCO-ETHERLIKE-EXT-MIB."
    REVISION        "201010290000Z"
    DESCRIPTION
        "Add capability statement ceeCapV12R0250SYPCat6K."
    REVISION        "201003120000Z"
    DESCRIPTION
        "Initial version of this MIB module."
    ::= { ciscoAgentCapability 587 }



ceeCapV12R0233SXI4PCat6K AGENT-CAPABILITIES
    PRODUCT-RELEASE "Cisco IOS 12.2(33)SXI4 on Catalyst 6000/6500
                         series devices."
    STATUS          current
    DESCRIPTION
        "CISCO-ETHERLIKE-EXT-MIB agent capabilities."

    SUPPORTS        CISCO-ETHERLIKE-EXT-MIB
    INCLUDES        { ciscoEtherExtPauseGroup }
    ::= { ciscoEtherlikeExtCapability 1 }

ceeCapV12R0250SYPCat6K AGENT-CAPABILITIES
    PRODUCT-RELEASE "Cisco IOS 12.2(50)SY on Catalyst 6000/6500
                         series devices."
    STATUS          current
    DESCRIPTION
        "CISCO-ETHERLIKE-EXT-MIB agent capabilities."

    SUPPORTS        CISCO-ETHERLIKE-EXT-MIB
    INCLUDES        { ciscoEtherExtPauseGroup }
    ::= { ciscoEtherlikeExtCapability 2 }

END
