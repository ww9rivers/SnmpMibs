-- *****************************************************************
--
-- ciscoSystemCapabilities MIB
--
-- AGENT-CAPABILITIES mib for CISCO-SYSTEM-MIB
--
-- March 2002, Subra Hegde
--
-- Copyright(c) 2002, 2003, 2007-2008 by Cisco Systems Inc.
--
-- ****************************************************************

CISCO-SYSTEM-CAPABILITY DEFINITIONS ::= BEGIN

IMPORTS
    MODULE-IDENTITY
        FROM SNMPv2-SMI
    AGENT-CAPABILITIES
        FROM SNMPv2-CONF
    ciscoAgentCapability
        FROM CISCO-SMI;


ciscoSystemCapability MODULE-IDENTITY
    LAST-UPDATED    "200807020000Z"
    ORGANIZATION    "Cisco Systems, Inc."
    CONTACT-INFO
            "Cisco Systems
            Customer Service

            Postal: 170 W Tasman Drive
            San Jose, CA  95134
            USA

            Tel: +1 800 553-NETS

            E-mail: cs-snmp@cisco.com,
            cs-lan-switch-snmp@cisco.com"
    DESCRIPTION
        "The Agent Capabilities for CISCO-SYSTEM-MIB."
    REVISION        "200807020000Z"
    DESCRIPTION
        "Added ciscoSystemCapACSWV03R000 agent capabilities for
        Application Control Engine (ACE) Module.

        Added ciscoSystemCapc4710aceVA1R700 agent capabilities for
        ACE 4710 Application Control Engine Appliance."
    REVISION        "200707310000Z"
    DESCRIPTION
        "Added ciscoSystemCapabilityMGXV5R0500."
    REVISION        "200309150000Z"
    DESCRIPTION
        "Added ciscoSystemCapCatOSV08R0101."
    REVISION        "200203060000Z"
    DESCRIPTION
        "Initial version of the MIB module."
    ::= { ciscoAgentCapability 276 }



ciscoSystemCapabilityV2R00 AGENT-CAPABILITIES
    PRODUCT-RELEASE "MGX8850 Release 2.00,
                         BPX SES Release 1.00"
    STATUS          current
    DESCRIPTION
        "CISCO-SYSTEM-MIB capabilities."

    SUPPORTS        CISCO-SYSTEM-MIB
    INCLUDES        {
                        ciscoSystemClockGroup,
                        ciscoSystemLocationGroup
                    }
    ::= { ciscoSystemCapability 1 }

ciscoSystemCapCatOSV08R0101 AGENT-CAPABILITIES
    PRODUCT-RELEASE "Cisco CatOS 8.1(1)."
    STATUS          current
    DESCRIPTION
        "CISCO-SYSTEM-MIB capabilities."

    SUPPORTS        CISCO-SYSTEM-MIB
    INCLUDES        {
                        ciscoSystemClockGroup,
                        ciscoSystemLocationGroup,
                        ciscoSystemSummerTimeGroup,
                        ciscoSystemScheduledResetGroup,
                        ciscoSystemSnmpAuthGroup,
                        ciscoSystemGeneralGroup,
                        ciscoSystemNotificationsGroup
                    }
    VARIATION       csySnmpAuthFailAddressType
    SYNTAX          INTEGER  {
                        ipv4(1)
                    }
    DESCRIPTION
        "Implementation only supports IPv4 addresses."

    ::= { ciscoSystemCapability 2 }

ciscoSystemCapabilityMGXV5R0500 AGENT-CAPABILITIES
    PRODUCT-RELEASE "MGX8850 5.5 Release"
    STATUS          current
    DESCRIPTION
        "CISCO-SYSTEM-MIB capabilities."

    SUPPORTS        CISCO-SYSTEM-MIB
    INCLUDES        {
                        ciscoSystemClockGroup,
                        ciscoSystemLocationGroup,
                        ciscoSystemSummerTimeGroupRev1
                    }
    VARIATION       csySummerTimeOffset
    ACCESS          not-implemented
    DESCRIPTION
        "Not Supported."

    ::= { ciscoSystemCapability 3 }

ciscoSystemCapACSWV03R000 AGENT-CAPABILITIES
    PRODUCT-RELEASE "ACSW (Application Control Software)
                    version 3.0(0)A1(2)."
    STATUS          current
    DESCRIPTION
        "CISCO-SYSTEM-MIB capabilities."

    SUPPORTS        CISCO-SYSTEM-MIB
    INCLUDES        {
                        ciscoSystemClockGroup,
                        ciscoSystemLocationGroup
                    }
    VARIATION       csyClockDateAndTime
    ACCESS          read-only
    DESCRIPTION
        "Set operation not allowed."

    VARIATION       csyLocationCountry
    ACCESS          read-only
    DESCRIPTION
        "Set operation not allowed."

    ::= { ciscoSystemCapability 4 }

ciscoSystemCapc4710aceVA1R700 AGENT-CAPABILITIES
    PRODUCT-RELEASE "ACSW (Application Control Software) A1(7)
                    for ACE 4710 Application Control Engine Appliance."
    STATUS          current
    DESCRIPTION
        "CISCO-SYSTEM-MIB capabilities."

    SUPPORTS        CISCO-SYSTEM-MIB
    INCLUDES        {
                        ciscoSystemClockGroup,
                        ciscoSystemLocationGroup
                    }
    VARIATION       csyClockDateAndTime
    ACCESS          read-only
    DESCRIPTION
        "Set operation not allowed."

    VARIATION       csyLocationCountry
    ACCESS          read-only
    DESCRIPTION
        "Set operation not allowed."

    ::= { ciscoSystemCapability 5 }

END
