-- *****************************************************************
-- CISCO-LWAPP-RF-CAPABILITY.my:
-- CISCO-LWAPP-RF MIB CAPABILITIES
--
-- Feb 2012 -  Venkatesh Puranik
--
-- Copyright (c) 2012 by cisco Systems Inc.
-- All rights reserved.
--
-- *****************************************************************

CISCO-LWAPP-RF-CAPABILITY DEFINITIONS ::= BEGIN

IMPORTS
    MODULE-IDENTITY
        FROM SNMPv2-SMI
    AGENT-CAPABILITIES
        FROM SNMPv2-CONF
    ciscoAgentCapability
        FROM CISCO-SMI;


ciscoLwappRFCapability MODULE-IDENTITY
    LAST-UPDATED    "201202280000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for CISCO-LWAPP-RF-MIB."
    REVISION        "201202280000Z"
    DESCRIPTION
        "Initial version of this MIB module."
    ::= { ciscoAgentCapability 23999 }


ciscoLwappRFCapabilityCUWNSV7R3 AGENT-CAPABILITIES
    PRODUCT-RELEASE "Cisco Unified Wireless Network Software
                     Release 7.3 for Cisco WLAN Controllers"
    STATUS          current
    DESCRIPTION
        "CISCO-LWAPP-RF-MIB capabilities."

    SUPPORTS        CISCO-LWAPP-RF-MIB
    INCLUDES        {
                        ciscoLwappRFConfigGroup,
                        ciscoLwappRFConfigGroup1,
                        ciscoLwappRFGlobalConfigGroup
                    }

    VARIATION     cLRFProfileHighDensityMaxRadioClients
    DESCRIPTION
        "The range of values supported are
        1 to 200."

    VARIATION     cLRFProfileBandSelectCycleCount
    DESCRIPTION
        "The range of values supported are
        1 to 10."

    VARIATION     cLRFProfileBandSelectCycleThreshold
    DESCRIPTION
        "The range of values supported are
        1 to 1000."

    VARIATION     cLRFProfileBandSelectExpireSuppression
    DESCRIPTION
        "The range of values supported are
        10 to 200."

    VARIATION     cLRFProfileBandSelectExpireDualBand
    DESCRIPTION
        "The range of values supported are
        10 to 300."

    VARIATION     cLRFProfileBandSelectClientRSSI
    DESCRIPTION
        "The range of values supported are
        -90 to -20."

    VARIATION    cLRFProfileLoadBalancingWindowSize
    DESCRIPTION
        "The range of values supported are
        0 to 20."

    VARIATION    cLRFProfileLoadBalancingDenialCount
    DESCRIPTION
        "The range of values supported are
        1 to 10."

    VARIATION    cLRFProfileCHDDataRSSIThreshold
    DESCRIPTION
        "The range of values supported are
        -90 to -60."

    VARIATION    cLRFProfileCHDVoiceRSSIThreshold
    DESCRIPTION
        "The range of values supported are
        -90 to -60."

    VARIATION    cLRFProfileCHDClientExceptionLevel
    DESCRIPTION
        "The range of values supported are
        1 to 75."

    VARIATION    cLRFProfileCHDCoverageExceptionLevel
    DESCRIPTION
        "The range of values supported are
        0 to 100."

    VARIATION    cLRFProfileMulticastDataRate
    DESCRIPTION
        "The range of values supported are
        0 to 54."

    ::= { ciscoLwappRFCapability 1 }

END
