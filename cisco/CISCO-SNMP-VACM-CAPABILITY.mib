-- *****************************************************************
-- CISCO-SNMP-VACM-CAPABILITY.my:
-- Cisco SNMP-VIEW-BASED-ACM-MIB AGENT-CAPABILITIES
--
-- September 2003, Binh Le
--
-- Copyright (c) 2003, 2006-2008 by Cisco Systems, Inc.
-- All rights reserved.
-- *****************************************************************

CISCO-SNMP-VACM-CAPABILITY DEFINITIONS ::= BEGIN

IMPORTS
    MODULE-IDENTITY
        FROM SNMPv2-SMI
    AGENT-CAPABILITIES
        FROM SNMPv2-CONF
    ciscoAgentCapability
        FROM CISCO-SMI;


ciscoSnmpVacmCapability MODULE-IDENTITY
    LAST-UPDATED    "200808040000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com, cs-snmp@cisco.com"
    DESCRIPTION
        "The capabilities description of
        SNMP-VIEW-BASED-ACM-MIB."
    REVISION        "200808040000Z"
    DESCRIPTION
        "Added capability statement
        ciscoSnmpVacmCapc4710aceVA1R700 for ACE 4710
        Application Control Engine Appliance."
    REVISION        "200706220000Z"
    DESCRIPTION
        "Added the correct mib name under the SUPPORTS
        clause for ciscoSnmpVacmCapCatOSV05R0501 and
        ciscoSnmpVacmCapACSWV03R000."
    REVISION        "200605220000Z"
    DESCRIPTION
        "Added capability statement
        ciscoSnmpVacmCapACSWV03R000 for
        Application Control Engine (ACE)."
    REVISION        "200309050000Z"
    DESCRIPTION
        "Initial version of this MIB module."
    ::= { ciscoAgentCapability 333 }



ciscoSnmpVacmCapCatOSV05R0501 AGENT-CAPABILITIES
    PRODUCT-RELEASE "Cisco CatOS 5.5(1)."
    STATUS          current
    DESCRIPTION
        "SNMP-VIEW-BASED-ACM-MIB capabilities."

    SUPPORTS        SNMP-VIEW-BASED-ACM-MIB
    INCLUDES        { vacmBasicGroup }
    VARIATION       vacmSecurityModel
    SYNTAX          INTEGER (1..3)
    DESCRIPTION
        "Only support SNMPv1 (1), SNMPv2c (2) and
        User-Based Security Model (3)."

    VARIATION       vacmSecurityToGroupStorageType
    SYNTAX          INTEGER  {
                        volatile(2),
                        nonVolatile(3),
                        readOnly(5)
                    }
    DESCRIPTION
        "Only support volatile(2), nonVolatile(3) and
        readOnly(5)."

    VARIATION       vacmAccessSecurityModel
    SYNTAX          INTEGER (1..3)
    DESCRIPTION
        "Only support SNMPv1 (1), SNMPv2c (2) and
        User-Based Security Model (3)."

    VARIATION       vacmAccessStorageType
    SYNTAX          INTEGER  {
                        volatile(2),
                        nonVolatile(3),
                        readOnly(5)
                    }
    DESCRIPTION
        "Only support volatile(2), nonVolatile(3) and
        readOnly(5)."

    VARIATION       vacmViewTreeFamilySubtree
    DESCRIPTION
        "Maximum OID length supported is 20."

    VARIATION       vacmViewTreeFamilyMask
    SYNTAX          OCTET STRING (SIZE (0..3))
    DESCRIPTION
        "Maxinum length supported is 3 octets."

    VARIATION       vacmViewTreeFamilyStorageType
    SYNTAX          INTEGER  {
                        volatile(2),
                        nonVolatile(3),
                        readOnly(5)
                    }
    DESCRIPTION
        "Only support volatile(2), nonVolatile(3) and
        readOnly(5)."

    ::= { ciscoSnmpVacmCapability 1 }

ciscoSnmpVacmCapACSWV03R000 AGENT-CAPABILITIES
    PRODUCT-RELEASE "ACSW (Application Control Software) 3.0"
    STATUS          current
    DESCRIPTION
        "SNMP-VIEW-BASED-ACM-MIB capabilities."

    SUPPORTS        SNMP-VIEW-BASED-ACM-MIB
    INCLUDES        { vacmBasicGroup }
    VARIATION       vacmGroupName
    ACCESS          read-only
    DESCRIPTION
        "Create operation not allowed via SNMP."

    VARIATION       vacmSecurityToGroupStorageType
    ACCESS          read-only
    DESCRIPTION
        "Create operation not allowed via SNMP."

    VARIATION       vacmSecurityToGroupStatus
    ACCESS          read-only
    DESCRIPTION
        "Create operation not allowed via SNMP."

    VARIATION       vacmAccessContextMatch
    ACCESS          read-only
    DESCRIPTION
        "Create operation not allowed via SNMP."

    VARIATION       vacmAccessReadViewName
    ACCESS          read-only
    DESCRIPTION
        "Create operation not allowed via SNMP."

    VARIATION       vacmAccessWriteViewName
    ACCESS          read-only
    DESCRIPTION
        "Create operation not allowed via SNMP."

    VARIATION       vacmAccessNotifyViewName
    ACCESS          read-only
    DESCRIPTION
        "Create operation not allowed via SNMP."

    VARIATION       vacmAccessStorageType
    ACCESS          read-only
    DESCRIPTION
        "Create operation not allowed via SNMP."

    VARIATION       vacmAccessStatus
    ACCESS          read-only
    DESCRIPTION
        "Create operation not allowed via SNMP."

    VARIATION       vacmViewSpinLock
    ACCESS          not-implemented
    DESCRIPTION
        "Not implemented as vacmViewTreeFamilyTable
        for the current implementation of the MIB has
        read-only support."

    VARIATION       vacmViewTreeFamilyMask
    ACCESS          read-only
    DESCRIPTION
        "Create operation not allowed via SNMP."

    VARIATION       vacmViewTreeFamilyType
    ACCESS          read-only
    DESCRIPTION
        "Create operation not allowed via SNMP."

    VARIATION       vacmViewTreeFamilyStorageType
    ACCESS          read-only
    DESCRIPTION
        "Create operation not allowed via SNMP."

    VARIATION       vacmViewTreeFamilyStatus
    ACCESS          read-only
    DESCRIPTION
        "Create operation not allowed via SNMP."

    ::= { ciscoSnmpVacmCapability 2 }

ciscoSnmpVacmCapc4710aceVA1R700 AGENT-CAPABILITIES
    PRODUCT-RELEASE "ACSW (Application Control Software) A1(7)
                         for ACE 4710 Application Control Engine
                         Appliance."
    STATUS          current
    DESCRIPTION
        "SNMP-VIEW-BASED-ACM-MIB capabilities."

    SUPPORTS        SNMP-VIEW-BASED-ACM-MIB
    INCLUDES        { vacmBasicGroup }
    VARIATION       vacmGroupName
    ACCESS          read-only
    DESCRIPTION
        "Create operation not allowed via SNMP."

    VARIATION       vacmSecurityToGroupStorageType
    ACCESS          read-only
    DESCRIPTION
        "Create operation not allowed via SNMP."

    VARIATION       vacmSecurityToGroupStatus
    ACCESS          read-only
    DESCRIPTION
        "Create operation not allowed via SNMP."

    VARIATION       vacmAccessContextMatch
    ACCESS          read-only
    DESCRIPTION
        "Create operation not allowed via SNMP."

    VARIATION       vacmAccessReadViewName
    ACCESS          read-only
    DESCRIPTION
        "Create operation not allowed via SNMP."

    VARIATION       vacmAccessWriteViewName
    ACCESS          read-only
    DESCRIPTION
        "Create operation not allowed via SNMP."

    VARIATION       vacmAccessNotifyViewName
    ACCESS          read-only
    DESCRIPTION
        "Create operation not allowed via SNMP."

    VARIATION       vacmAccessStorageType
    ACCESS          read-only
    DESCRIPTION
        "Create operation not allowed via SNMP."

    VARIATION       vacmAccessStatus
    ACCESS          read-only
    DESCRIPTION
        "Create operation not allowed via SNMP."

    VARIATION       vacmViewSpinLock
    ACCESS          not-implemented
    DESCRIPTION
        "Not implemented as vacmViewTreeFamilyTable
        for the current implementation of the MIB has
        read-only support."

    VARIATION       vacmViewTreeFamilyMask
    ACCESS          read-only
    DESCRIPTION
        "Create operation not allowed via SNMP."

    VARIATION       vacmViewTreeFamilyType
    ACCESS          read-only
    DESCRIPTION
        "Create operation not allowed via SNMP."

    VARIATION       vacmViewTreeFamilyStorageType
    ACCESS          read-only
    DESCRIPTION
        "Create operation not allowed via SNMP."

    VARIATION       vacmViewTreeFamilyStatus
    ACCESS          read-only
    DESCRIPTION
        "Create operation not allowed via SNMP."

    ::= { ciscoSnmpVacmCapability 3 }

END
