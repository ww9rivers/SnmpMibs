-- *****************************************************************
-- CISCO-UDLDP-CAPABILITY.my:
-- Cisco CISCO-UDLDP-MIB AGENT-CAPABILITIES
--
-- April 2004, Padma Pullela
--
-- Copyright (c) 2004, 2010 by Cisco Systems, Inc.
-- All rights reserved.
-- *****************************************************************

CISCO-UDLDP-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoUdldpCapability MODULE-IDENTITY
    LAST-UPDATED    "201003160900Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-UDLDP-MIB."
    REVISION        "201003160900Z"
    DESCRIPTION
        "Added capability statement ciscoUdldpCapV12R0233SXI4PCat6K."
    REVISION        "200404070000Z"
    DESCRIPTION
        "Initial version of this MIB module."
    ::= { ciscoAgentCapability 344 }



ciscoUdldpCapV12R0214SXCat6K AGENT-CAPABILITIES
    PRODUCT-RELEASE "Cisco IOS 12.2(14SX) on Catalyst 6000/6500
                         and Cisco 7600 series devices."
    STATUS          current
    DESCRIPTION
        "CISCO-UDLDP-MIB capabilities."

    SUPPORTS        CISCO-UDLDP-MIB
    INCLUDES        { ciscoUdldpMIBGroup2 }
    ::= { ciscoUdldpCapability 1 }

ciscoUdldpCapCatOSV07R0604 AGENT-CAPABILITIES
    PRODUCT-RELEASE "Cisco CatOS 7.6(4)."
    STATUS          current
    DESCRIPTION
        "CISCO-UDLDP-MIB capabilities."

    SUPPORTS        CISCO-UDLDP-MIB
    INCLUDES        {
                        ciscoUdldpMIBGroup,
                        ciscoUdldpAggreModeOptionalGroup
                    }
    ::= { ciscoUdldpCapability 2 }

ciscoUdldpCapCatOSV08R0101 AGENT-CAPABILITIES
    PRODUCT-RELEASE "Cisco CatOS 8.1(1)."
    STATUS          current
    DESCRIPTION
        "CISCO-UDLDP-MIB capabilities."

    SUPPORTS        CISCO-UDLDP-MIB
    INCLUDES        {
                        ciscoUdldpMIBGroup,
                        ciscoUdldpAggreModeOptionalGroup,
                        ciscoUdldpMIBGroup2
                    }
    VARIATION       cudldpGlobalMode
    SYNTAX          INTEGER  {
                        enable(1),
                        disable(2)
                    }
    DESCRIPTION
        "Only limited set of enumerated values is supported."

    VARIATION       cudldpInterfaceAdminMode
    SYNTAX          INTEGER  {
                        enable(1),
                        disable(2),
                        aggressive(3)
                    }
    DESCRIPTION
        "Only limited set of enumerated values is supported."

    ::= { ciscoUdldpCapability 3 }

ciscoUdldpCapV12R0233SXI4PCat6K AGENT-CAPABILITIES
    PRODUCT-RELEASE "Cisco IOS 12.2(33)SXI4 on Catalyst 6000/6500
                     series devices running IOS images."
    STATUS          current
    DESCRIPTION
        "CISCO-UDLDP-MIB capabilities."

    SUPPORTS        CISCO-UDLDP-MIB
    INCLUDES        {
                        ciscoUdldpMIBGroup2,
                        ciscoUdldpFastHelloGroup,
                        ciscoUdldpFastHelloNotificationGroup
                    }
    VARIATION       cudldpIfFastHelloInterval
    SYNTAX          Unsigned32 (0 | 200..1000)
    DESCRIPTION
        "Only limited set of values is supported."

    ::= { ciscoUdldpCapability 4 }

END
