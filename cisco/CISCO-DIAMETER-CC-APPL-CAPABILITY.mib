-- *****************************************************************
-- CISCO-DIAMETER-CC-APPL-CAPABILITY.my:  Cisco Diameter Credit
-- Control Application MIB AGENT-CAPABILITIES
--
-- September 05, 2006 - Subash T.Comerica
--
-- Copyright (c) 2006 by Cisco Systems, Inc.
-- All rights reserved.
--
-- *****************************************************************

CISCO-DIAMETER-CC-APPL-CAPABILITY DEFINITIONS ::= BEGIN

IMPORTS
    MODULE-IDENTITY
        FROM SNMPv2-SMI
    AGENT-CAPABILITIES
        FROM SNMPv2-CONF
    ciscoAgentCapability
        FROM CISCO-SMI;


ciscoDiameterCCACapability MODULE-IDENTITY
    LAST-UPDATED    "200609060000Z"
    ORGANIZATION    "Cisco Systems, Inc."
    CONTACT-INFO
            "Cisco Systems
            Customer Service

            Postal: 170 W Tasman Drive
            San Jose, CA  95134
            USA

            Tel: +1 800 553-NETS

            E-mail: cs-aaa@cisco.com"
    DESCRIPTION
            "The capabilities description of
            CISCO-DIAMETER-CC-AAPL-MIB."
    REVISION        "200609060000Z"
    DESCRIPTION
            "Initial version of this MIB module."
          ::= { ciscoAgentCapability 516 }



ciscoDiameterCCACapabilityV12R0409XG AGENT-CAPABILITIES
    PRODUCT-RELEASE "Cisco IOS 12.4(9)XG."
    STATUS          current
    DESCRIPTION
            "Cisco Diameter Credit Control Application MIB capabilities"

    SUPPORTS        CISCO-DIAMETER-CC-APPL-MIB
    INCLUDES        {
                        ciscoDiameterCCAHostCfgGroup,
                        ciscoDiameterCCAPeerCfgGroup,
                        ciscoDiameterCCAPeerStatsGroup
                    }
    VARIATION       cdccaHostIpAddrType
    ACCESS          not-implemented
    DESCRIPTION     "This object is not supported."

    VARIATION       cdccaHostIpAddress
    ACCESS          not-implemented
    DESCRIPTION     "This object is not supported."

    VARIATION       cdccaHostId
    ACCESS          not-implemented
    DESCRIPTION     "This object is not supported."

    VARIATION       cdccaPeerId
    ACCESS          not-implemented
    DESCRIPTION     "This object is not supported."

    VARIATION       cdccaPeerVendorId
    ACCESS          not-implemented
    DESCRIPTION     "This object is not supported."

    VARIATION       cdccaPeerStorageType
    ACCESS          not-implemented
    DESCRIPTION     "This object is not supported."

    VARIATION       cdccaPeerVendorStorageType
    ACCESS          not-implemented
    DESCRIPTION     "This object is not supported."

    VARIATION       cdccaPeerFirmwareRevision
    ACCESS          not-implemented
    DESCRIPTION     "This object is not supported."

    VARIATION       cdccaPeerRowStatus
    ACCESS          not-implemented
    DESCRIPTION     "This object is not supported."

    VARIATION       cdccaPeerVendorRowStatus
    ACCESS          not-implemented
    DESCRIPTION     "This object is not supported."

    VARIATION       cdccaPeerStatsCCRDropped
    ACCESS          not-implemented
    DESCRIPTION     "This object is not supported."

    VARIATION       cdccaPeerStatsCCADropped
    ACCESS          not-implemented
    DESCRIPTION     "This object is not supported."

    VARIATION       cdccaPeerStatsRARDropped
    ACCESS          not-implemented
    DESCRIPTION     "This object is not supported."

    VARIATION       cdccaPeerStatsRAADropped
    ACCESS          not-implemented
    DESCRIPTION     "This object is not supported."

    VARIATION       cdccaPeerStatsSTRDropped
    ACCESS          not-implemented
    DESCRIPTION     "This object is not supported."

    VARIATION       cdccaPeerStatsSTADropped
    ACCESS          not-implemented
    DESCRIPTION     "This object is not supported."

    VARIATION       cdccaPeerStatsAAROut
    ACCESS          not-implemented
    DESCRIPTION     "This object is not supported."

    VARIATION       cdccaPeerStatsAARDropped
    ACCESS          not-implemented
    DESCRIPTION     "This object is not supported."

    VARIATION       cdccaPeerStatsAAAIn
    ACCESS          not-implemented
    DESCRIPTION     "This object is not supported."

    VARIATION       cdccaPeerStatsAAADropped
    ACCESS          not-implemented
    DESCRIPTION     "This object is not supported."

    VARIATION       cdccaPeerStatsASRDropped
    ACCESS          not-implemented
    DESCRIPTION     "This object is not supported."

    VARIATION       cdccaPeerStatsASADropped
    ACCESS          not-implemented
    DESCRIPTION     "This object is not supported."

    ::= { ciscoDiameterCCACapability 1 }

END
