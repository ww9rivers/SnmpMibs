--
-- This SMIv1 module has been generated by smidump 0.4.1. Do not edit.
--

BRWAVE-RADIO-MIB DEFINITIONS ::= BEGIN

IMPORTS
    ifIndex
        FROM IF-MIB
    OBJECT-TYPE
        FROM RFC-1212
    TRAP-TYPE
        FROM RFC-1215
    enterprises
        FROM SNMPv2-SMI
    DisplayString
        FROM SNMPv2-TC;

brwaveRadioMibModule OBJECT IDENTIFIER
    ::= { brwaveMibs 3 }

-- brwaveRadioMibModule MODULE-IDENTITY
--     LAST-UPDATED "200607061100Z"
--     ORGANIZATION 
--         "BridgeWave Communications"
--     CONTACT-INFO 
--         "
--          Postal: BridgeWave Communications
--             		3350 Thomas Road
--          				Santa Clara, CA 95054
--          				USA
--             Tel:    +1 408 567 6900
--             Fax:    +1 408 567 0775
--             Web:    www.bridgewave.com
--             "
--     DESCRIPTION 
--         "Radio MIB module."
--     REVISION    "200607061100Z"
--     DESCRIPTION 
--         "Combined ROOT/RADIO mib in one module."
--     REVISION    "200505261130Z"
--     DESCRIPTION 
--         "Radio MIB module created."
--     ::= { brwaveMibs 3 }


bridgeWave OBJECT IDENTIFIER
    ::= { enterprises 6080 }

brwaveReg OBJECT IDENTIFIER
    ::= { bridgeWave 1 }

brwaveMibs OBJECT IDENTIFIER
    ::= { brwaveReg 1 }

brwaveModules OBJECT IDENTIFIER
    ::= { brwaveReg 2 }

brwaveRadioFE60 OBJECT IDENTIFIER
    ::= { brwaveModules 1 }

brwaveRadioGE60 OBJECT IDENTIFIER
    ::= { brwaveModules 2 }

brwaveRadioAR60 OBJECT IDENTIFIER
    ::= { brwaveModules 3 }

brwaveCommon OBJECT IDENTIFIER
    ::= { bridgeWave 2 }

brwaveRadioSn OBJECT-TYPE
    SYNTAX      DisplayString
    ACCESS      read-only
    STATUS      mandatory
    DESCRIPTION 
        "Radio serial number."
    ::= { brwaveCommon 1 }

brwaveUnitModel OBJECT-TYPE
    SYNTAX      DisplayString
    ACCESS      read-only
    STATUS      mandatory
    DESCRIPTION 
        "Unit's model."
    ::= { brwaveCommon 2 }

brwaveBbSn OBJECT-TYPE
    SYNTAX      DisplayString
    ACCESS      read-only
    STATUS      mandatory
    DESCRIPTION 
        "Base Band hardware serial number"
    ::= { brwaveCommon 3 }

brwaveIfSn OBJECT-TYPE
    SYNTAX      DisplayString
    ACCESS      read-only
    STATUS      mandatory
    DESCRIPTION 
        "IF hardware serial number"
    ::= { brwaveCommon 4 }

brwaveMmwSn OBJECT-TYPE
    SYNTAX      DisplayString
    ACCESS      read-only
    STATUS      mandatory
    DESCRIPTION 
        "MMW Hardware serial number"
    ::= { brwaveCommon 5 }

brwaveTrapCount OBJECT-TYPE
    SYNTAX      Gauge
    ACCESS      read-only
    STATUS      mandatory
    DESCRIPTION 
        "Number of traps generated by unit since start-up.
         Rolls back to zero once reached to maximum value."
    ::= { brwaveCommon 6 }

brwaveProducts OBJECT IDENTIFIER
    ::= { bridgeWave 3 }

brwaveRadio OBJECT IDENTIFIER
    ::= { brwaveProducts 1 }

brwaveRadioFactorySetup OBJECT IDENTIFIER
    ::= { brwaveRadio 2 }

brwaveRadioTxBand OBJECT-TYPE
    SYNTAX      INTEGER { low(1), high(2) }
    ACCESS      read-only
    STATUS      mandatory
    DESCRIPTION 
        "Radio Link Transmit frequency."
    ::= { brwaveRadioFactorySetup 1 }

brwaveRadioFactoryRate OBJECT-TYPE
    SYNTAX      INTEGER { adaptRate(1), mbps1000(2), mbps100(3) }
    ACCESS      read-only
    STATUS      mandatory
    DESCRIPTION 
        "Factory configured radio link rate."
    ::= { brwaveRadioFactorySetup 3 }

brwaveRadioClearStats OBJECT-TYPE
    SYNTAX      INTEGER
    ACCESS      read-write
    STATUS      mandatory
    DESCRIPTION 
        "Clear Statistics, Set value of 1 to clear.
         Returns always 0 when read."
    ::= { brwaveRadioFactorySetup 4 }

brwaveRadioStatus OBJECT IDENTIFIER
    ::= { brwaveRadio 3 }

brwaveRadioInVoltage OBJECT-TYPE
    SYNTAX      INTEGER
    ACCESS      read-only
    STATUS      mandatory
    DESCRIPTION 
        "Input voltage. The reading of the unit's input voltage
         level in Volts x100."
    ::= { brwaveRadioStatus 1 }

brwaveRadioUnitTemperature OBJECT-TYPE
    SYNTAX      INTEGER
    ACCESS      read-only
    STATUS      mandatory
    DESCRIPTION 
        "Unit Temperature. The reading of the temperature sensor
         in degrees C x 100."
    ::= { brwaveRadioStatus 2 }

brwaveRadioTxTemperature OBJECT-TYPE
    SYNTAX      INTEGER
    ACCESS      read-only
    STATUS      mandatory
    DESCRIPTION 
        "Radio Transmiter Temperature. The reading of the radio
         temperature sensor in degrees C x 100."
    ::= { brwaveRadioStatus 3 }

brwaveRadioRSL OBJECT-TYPE
    SYNTAX      INTEGER
    ACCESS      read-only
    STATUS      mandatory
    DESCRIPTION 
        "Received Signal Level. The signal level of the received
         radio frequency in dBm x 100"
    ::= { brwaveRadioStatus 4 }

brwaveRadioRSLVoltage OBJECT-TYPE
    SYNTAX      DisplayString
    ACCESS      read-only
    STATUS      mandatory
    DESCRIPTION 
        "Received Signal Level measured as Voltage."
    ::= { brwaveRadioStatus 5 }

brwaveRadioAbsRSL OBJECT-TYPE
    SYNTAX      INTEGER
    ACCESS      read-only
    STATUS      mandatory
    DESCRIPTION 
        "Received Signal Level. The signal level of the received
         radio frequency in dBm x 100"
    ::= { brwaveRadioStatus 6 }

brwaveRadioRSLVoltageInt OBJECT-TYPE
    SYNTAX      INTEGER
    ACCESS      read-only
    STATUS      mandatory
    DESCRIPTION 
        "Received Signal Level measured as Voltage."
    ::= { brwaveRadioStatus 7 }

brwaveCopperUtilization OBJECT-TYPE
    SYNTAX      INTEGER
    ACCESS      read-only
    STATUS      mandatory
    DESCRIPTION 
        "Link utilization calculated every polling interval."
    ::= { brwaveRadioStatus 8 }

brwaveFiberUtilization OBJECT-TYPE
    SYNTAX      INTEGER
    ACCESS      read-only
    STATUS      mandatory
    DESCRIPTION 
        "Link utilization calculated every polling interval."
    ::= { brwaveRadioStatus 9 }

brwaveRadioUtilization OBJECT-TYPE
    SYNTAX      INTEGER
    ACCESS      read-only
    STATUS      mandatory
    DESCRIPTION 
        "Link utilization calculated every polling interval."
    ::= { brwaveRadioStatus 10 }

brwaveRadioFecError OBJECT-TYPE
    SYNTAX      INTEGER { noError(0), preFec(1), postFec(2) }
    ACCESS      read-only
    STATUS      mandatory
    DESCRIPTION 
        "Post and Pre FEC error calculated every polling interval
         0 - No Error, 1-Pre FEC Error, 2-Post FEC Error"
    ::= { brwaveRadioStatus 11 }

brwaveRadioPreFecFlag OBJECT-TYPE
    SYNTAX      INTEGER
    ACCESS      read-only
    STATUS      mandatory
    DESCRIPTION 
        "Pre FEC error flag every polling interval"
    ::= { brwaveRadioStatus 12 }

brwaveRadioPostFecFlag OBJECT-TYPE
    SYNTAX      INTEGER
    ACCESS      read-only
    STATUS      mandatory
    DESCRIPTION 
        "Post FEC error Flag every polling interval"
    ::= { brwaveRadioStatus 13 }

brwaveRadioLinkRate OBJECT-TYPE
    SYNTAX      INTEGER
    ACCESS      read-only
    STATUS      mandatory
    DESCRIPTION 
        "Radio Link Rate in Mbps."
    ::= { brwaveRadioStatus 14 }

brwaveRadioEvents OBJECT IDENTIFIER
    ::= { brwaveRadio 9 }

brwaveRadioEventsV2 OBJECT IDENTIFIER
    ::= { brwaveRadioEvents 0 }

brwaveRadioTrapObjs OBJECT IDENTIFIER
    ::= { brwaveRadioEvents 1 }

managerIP OBJECT-TYPE
    SYNTAX      OCTET STRING (SIZE(0..32))
    ACCESS      read-only
    STATUS      mandatory
    DESCRIPTION 
        "IP address of NMS station accessing the unit."
    ::= { brwaveRadioTrapObjs 1 }

userName OBJECT-TYPE
    SYNTAX      OCTET STRING (SIZE(0..32))
    ACCESS      read-only
    STATUS      mandatory
    DESCRIPTION 
        "User accessing the unit."
    ::= { brwaveRadioTrapObjs 2 }

brwaveConformance OBJECT IDENTIFIER
    ::= { brwaveRadio 10 }

brwaveRadioGroups OBJECT IDENTIFIER
    ::= { brwaveConformance 1 }

brwaveCompliances OBJECT IDENTIFIER
    ::= { brwaveConformance 2 }

brwaveErrorsOverThreshold TRAP-TYPE
    ENTERPRISE  brwaveRadioEvents
    VARIABLES   { ifIndex, brwaveRadioUnitTemperature, 
                  brwaveRadioTxTemperature, brwaveRadioRSL }
--     STATUS      mandatory
    DESCRIPTION 
        "Link has error rate over threshold."
    ::= 1

brwaveErrorsUnderThreshold TRAP-TYPE
    ENTERPRISE  brwaveRadioEvents
    VARIABLES   { ifIndex, brwaveRadioUnitTemperature, 
                  brwaveRadioTxTemperature, brwaveRadioRSL }
--     STATUS      mandatory
    DESCRIPTION 
        "Link error rate changed from over to under threshold ."
    ::= 2

brwaveUnitTemperatureAbnormal TRAP-TYPE
    ENTERPRISE  brwaveRadioEvents
    VARIABLES   { brwaveRadioUnitTemperature }
--     STATUS      mandatory
    DESCRIPTION 
        "Radio unit temperature not in normal operating range.
         Normal range is: -20 to +75 degree Centigrade."
    ::= 3

brwaveUnitTemperatureNormal TRAP-TYPE
    ENTERPRISE  brwaveRadioEvents
    VARIABLES   { brwaveRadioUnitTemperature }
--     STATUS      mandatory
    DESCRIPTION 
        "Unit temperature restores from abnormal to normal range."
    ::= 4

brwaveTxTemperatureAbnormal TRAP-TYPE
    ENTERPRISE  brwaveRadioEvents
    VARIABLES   { brwaveRadioTxTemperature }
--     STATUS      mandatory
    DESCRIPTION 
        "Transmitter temperature is not in normal operating range.
         Normal range is: -20 to +75 degree Centigrade."
    ::= 5

brwaveTxTemperatureNormal TRAP-TYPE
    ENTERPRISE  brwaveRadioEvents
    VARIABLES   { brwaveRadioTxTemperature }
--     STATUS      mandatory
    DESCRIPTION 
        "Transmitter temperature is restored to normal range."
    ::= 6

brwaveInputVoltageAbnormal TRAP-TYPE
    ENTERPRISE  brwaveRadioEvents
    VARIABLES   { brwaveRadioInVoltage }
--     STATUS      mandatory
    DESCRIPTION 
        "Unit's input voltage is not in normal range.
         Normal input voltage > 16 Volts."
    ::= 7

brwaveInputVoltageNormal TRAP-TYPE
    ENTERPRISE  brwaveRadioEvents
    VARIABLES   { brwaveRadioInVoltage }
--     STATUS      mandatory
    DESCRIPTION 
        "Unit's input voltage is restored to normal range."
    ::= 8

brwaveRslNormal TRAP-TYPE
    ENTERPRISE  brwaveRadioEvents
    VARIABLES   { brwaveRadioRSL }
--     STATUS      mandatory
    DESCRIPTION 
        "Received Signal Level is normal. Normal signal level
         RSL > -55.00 dBm (Gigabit) and RSL > -59.00 dBm (Fast Ethernet)."
    ::= 10

brwaveRslMinor TRAP-TYPE
    ENTERPRISE  brwaveRadioEvents
    VARIABLES   { brwaveRadioRSL }
--     STATUS      mandatory
    DESCRIPTION 
        "Received Signal Leve droped to the level of minor event.
         RSL from -55.00 to -59.00 dBm (GE Radio)
         RSL from -59.00 to -65.00 dBm (FE radio)."
    ::= 11

brwaveRslMajor TRAP-TYPE
    ENTERPRISE  brwaveRadioEvents
    VARIABLES   { brwaveRadioRSL }
--     STATUS      mandatory
    DESCRIPTION 
        "RSL droppped to the level of major event.
         RSL < -59.00 dBm (GE Radio) or RSL < -65 dBm (FE radio)."
    ::= 13

brwaveConfigChange TRAP-TYPE
    ENTERPRISE  brwaveRadioEvents
--     STATUS      mandatory
    DESCRIPTION 
        "Configuration changes are performed by WEB client."
    ::= 26

brwaveLoginSuccessfull TRAP-TYPE
    ENTERPRISE  brwaveRadioEvents
--     STATUS      mandatory
    DESCRIPTION 
        "NMS Loged in successfully."
    ::= 27

brwaveGeToFeSwitch TRAP-TYPE
    ENTERPRISE  brwaveRadioEvents
    VARIABLES   { brwaveRadioRSL }
--     STATUS      mandatory
    DESCRIPTION 
        "Tx Rate switched from GE to FE."
    ::= 28

brwaveFeToGeSwitch TRAP-TYPE
    ENTERPRISE  brwaveRadioEvents
    VARIABLES   { brwaveRadioRSL }
--     STATUS      mandatory
    DESCRIPTION 
        "Tx Rate switched from FE to GE."
    ::= 29

brwaveCommonGroup OBJECT IDENTIFIER
    ::= { brwaveRadioGroups 1 }

-- brwaveCommonGroup OBJECT-GROUP
--     OBJECTS     { brwaveRadioSn, brwaveUnitModel, brwaveTrapCount }
--     STATUS      mandatory
--     DESCRIPTION 
--         "Collection of common objects."
--     ::= { brwaveRadioGroups 1 }

brwaveFactoryGroup OBJECT IDENTIFIER
    ::= { brwaveRadioGroups 2 }

-- brwaveFactoryGroup OBJECT-GROUP
--     OBJECTS     { brwaveRadioTxBand }
--     STATUS      mandatory
--     DESCRIPTION 
--         "Collection of factory setup objects."
--     ::= { brwaveRadioGroups 2 }

brwaveStatusGroup OBJECT IDENTIFIER
    ::= { brwaveRadioGroups 3 }

-- brwaveStatusGroup OBJECT-GROUP
--     OBJECTS     { brwaveRadioInVoltage, brwaveRadioUnitTemperature, 
--                   brwaveRadioTxTemperature, brwaveRadioRSL, 
--                   brwaveRadioRSLVoltage }
--     STATUS      mandatory
--     DESCRIPTION 
--         "Collection of status objects."
--     ::= { brwaveRadioGroups 3 }

END -- end of module BRWAVE-RADIO-MIB.
